# Specification Title

# Specification: Specification Document
- Description: Requirements Document

## R1: A
every column filled
- bool_column: true
- string_column: text
- integer_column: 4
- real_column: 4.0
- date_column: 2019-02-23T11:27:58.000+01:00
- xhtml_column: text text2 text3Â
- enumeration_column_multi: B, C

## R2: B
nothing filled

## R3: C
default values filled
- bool_column_default: false
- string_column_default: other
- integer_column_default: 2
- real_column_default: 3.0
- date_column_default: 2004-04-24T01:20:00.000+02:00
- rel_type -> R8

## R4: D
filled like default
- bool_column_default: true
- integer_column_default: 1
- real_column_default: 2.0
- date_column_default: 2004-04-12T13:20:00.000+02:00

### R5: E
dummyE

#### R8: F
dummyF

##### R10: G
dummyG

#### R9: H
dummyH

### R6: I
dummyI

#### R7: J
dummyJ

## R11: K
dummyK
