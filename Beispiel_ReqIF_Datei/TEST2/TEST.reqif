# TEST

# Specification: NEEDS
- ReqIF.Description: ReqView User Needs

## NEEDS-3: User Stories (NEEDS Object Type)
- Type: Section

### NEEDS-9: Requirements Storage (NEEDS Object Type)
- Type: Section

#### NEEDS-58: Document Files (NEEDS Object Type)
- Acceptance Criteria: Tool supports:
  - saving project in a file
  - opening project from a file
- As a(n): Editor
- I want to: save document in a file
- So that: users can open the document for further editing or review
- Status: Verified
- Type: Requirement

#### NEEDS-14: Document Templates (NEEDS Object Type)
- Acceptance Criteria: Tool supports:
  - saving a document as a document template file,
  - add a new document into a project from a saved document template file while preserving document attributes definition, values of object attributes and object attachments.
- As a(n): Architect
- I want to: save a document as a template file
- So that: I can reuse the document structure and configuration of custom attributes for new documents
- Status: Verified
- Type: Requirement

#### NEEDS-33: Autosave (NEEDS Object Type)
- Acceptance Criteria: Tool:
  - instantly saves all the changes,
  - restores the same project content when it is restarted.
- As a(n): Editor
- I want to: automatically persist my changes
- So that: I do not lose my changes if the tool is unexpectedly terminated before saving into a file
- Status: Verified
- Type: Requirement

### NEEDS-8: Define Requirements (NEEDS Object Type)
- Type: Section

#### NEEDS-68: Requirement Description (NEEDS Object Type)
- Acceptance Criteria: Tool supports:
  - setting a description of a selected requirement
  - removing description of a selected requirement
- As a(n): Editor
- I want to: specify requirements by a textual description
- So that: the requirements can be reviewed by other users.
- Status: Verified
- Type: Requirement

#### NEEDS-32: Unique IDs (NEEDS Object Type)
- Acceptance Criteria: Tool supports:
  - automatic generation of document ID which can not be further changed
- As a(n): Editor
- I want to: identify requirements by their unique ID
- So that: I can reference requirements from other documents or communication
- Status: Verified
- Type: Requirement

#### NEEDS-12: Document Structure (NEEDS Object Type)
- Acceptance Criteria: Tool supports:
  - creation of a new project,
  - adding a new document into a project,
  - deletion of a document from a project.
- As a(n): Editor
- I want to: organize requirements in a tree document hierarchy with numbered sections
- So that: I can easily navigate in the document structure
- Status: Verified
- Type: Requirement

#### NEEDS-73: Table View (NEEDS Object Type)
- Acceptance Criteria: Tool supports:
  - displaying of requirements in a table,
  - displaying requirements ID, description, discussion, links and custom attributes in columns,
  - hiding requirements table columns,
  - reordering of requirements table columns,
  - resizing of requirements table columns.
- As a(n): Editor
- I want to: display a table of requirements
- So that: I can review all requirements information in a single view
- Status: Verified
- Type: Requirement

#### NEEDS-74: Detailed View (NEEDS Object Type)
- Acceptance Criteria: Tool supports:
  - displaying custom attributes of the selected requirement in a pane or dialog,
  - displaying discussion of the selected requirement in a pane or dialog,
  - displaying traceability links for the selected requirement in a pane or dialog,
  - displaying history of changes for the selected requirement in a pane or dialog.
- As a(n): Editor
- I want to: display all information about the selected requirement
- So that: I can display details about any requirement which are not visible in the requirements table
- Status: Verified
- Type: Requirement

#### NEEDS-17: Attachments (NEEDS Object Type)
- Acceptance Criteria: Tool supports:
  - attachment of image file to document objects,
  - displaying image attachments in the context of the related document object,
  - deletion of attachments
- As a(n): Editor
- I want to: attach images and other documents to requirements
- So that: I can enhance textual requirements with visual content such as mockups, diagrams, etc.
- Status: Verified
- Type: Requirement

#### NEEDS-35: Sort (NEEDS Object Type)
- Acceptance Criteria: Tool supports sorting requirements by:
  - the natural document order,
  - value of a custom attribute.
- As a(n): Editor
- I want to: order requirements by a chosen custom attribute
- So that: I can display requirements sorted by priority, risk, effort, etc.
- Status: Verified
- Type: Requirement

### NEEDS-70: Manage Requirements (NEEDS Object Type)
- Type: Section

#### NEEDS-19: Custom Attributes Configuration (NEEDS Object Type)
- Acceptance Criteria: Tool supports:
  - creation of a new custom attribute,
  - deletion of a custom attribute,
  - definition of following custom attribute types
  - number
  - date
  - boolean
  - single and multivalue enumeration
  - string / rich formatted text
- As a(n): Architect
- I want to: define additional requirements attributes
- So that: the document can flexibly store additional requirement properties, such as requirement source, priority, status, etc.
- Status: Verified
- Type: Requirement

#### NEEDS-69: Custom Attributes (NEEDS Object Type)
- Acceptance Criteria: Tool supports:
  - setting requirements source, priority, status and acceptance criteria
  - setting and resetting a value of a custom attribute for multiple requirements
- As a(n): Editor
- I want to: set a value of a chosen custom attribute for one or more selected requirements
- So that: I can define additional requirements properties, such as requirements source, prioritize requirements, manage requirement status, define acceptance criteria, etc.
- Status: Verified
- Type: Requirement

#### NEEDS-16: Traceability Configuration (NEEDS Object Type)
- Acceptance Criteria: Tool supports:
  - creation of at least one link type
  - definition of a start and end role for a link type
  - removal of a link type including all existing links
- As a(n): Architect
- I want to: define types of relationships between requirements
- So that: users can perform traceability analysis for a chosen group of links
- Status: Verified
- Type: Requirement

#### NEEDS-21: Traceability Links (NEEDS Object Type)
- Acceptance Criteria: Tool supports:
  - creation of links with chosen link type between selected requirements,
  - deletion of links
- As a(n): Editor
- I want to: link related requirements
- So that: I can analyze requirements coverage, gap in requirements and impact of requirement changes.
- Status: Verified
- Type: Requirement

#### NEEDS-34: Filter (NEEDS Object Type)
- Acceptance Criteria: Tool supports filtering requirements:
  - by full text search in the object heading, text or a custom attribute
  - with the given traceability link type
  - in the given section
- As a(n): Editor
- I want to: filter requirements
- So that: I can identify and manipulate requirements matching a condition
- Status: Verified
- Type: Requirement

#### NEEDS-36: Search (NEEDS Object Type)
- Acceptance Criteria: Tool supports searching requirements containing a given keyword.
- As a(n): Editor
- I want to: find keywords
- So that: I can identify and manipulate requirements containing the searched keyword(s)
- Status: Verified
- Type: Requirement

### NEEDS-22: Review Requirements (NEEDS Object Type)
- Type: Section

#### NEEDS-24: Discussion (NEEDS Object Type)
- Acceptance Criteria: Tool supports:
  - commenting a selected requirement,
  - displaying discussion for a selected requirement.
- As a(n): Reviewer
- I want to: comment requirements
- So that: I can provide feedback during requirements review
- Status: Verified
- Type: Requirement

#### NEEDS-30: Traceability Browser (NEEDS Object Type)
- Acceptance Criteria: Tool supports:
  - displaying linked requirements ordered by link type
  - changing focus to a selected requirement
  - filtering requirements with missing traceability links of a given link type
- As a(n): Reviewer
- I want to: trace related requirements
- So that: I can perform coverage, gap and change impact analysis
- Status: Verified
- Type: Requirement

#### NEEDS-29: Print (NEEDS Object Type)
- Acceptance Criteria: Tool supports:
  - printing a document with the same layout as it is displayed,
  - saving the document as PDF with the same layout as it is displayed.
- As a(n): Reviewer
- I want to: print a document view
- So that: I can review requirements without the need to run the tool
- Status: Verified
- Type: Requirement

### NEEDS-31: Audit Trail (NEEDS Object Type)
- Type: Section

#### NEEDS-26: History of Changes (NEEDS Object Type)
- Acceptance Criteria: Tool supports:
  - displaying history of changes for a selected requirement.
- As a(n): Editor
- I want to: list all requirement changes
- So that: I can understand how the requirement evolved in time
- Status: Verified
- Type: Requirement

#### NEEDS-23: Traceability Report (NEEDS Object Type)
- Acceptance Criteria: Tool supports:
  - generation of a custom traceability report which visualizes end-to-end requirements traceability
- As a(n): Reviewer
- I want to: generate a traceability report
- So that: I can analyze coverage, gaps and impact of requirements changes
- Status: Verified
- Type: Requirement

### NEEDS-11: Integrations (NEEDS Object Type)
- Type: Section

#### NEEDS-27: Import from Word (NEEDS Object Type)
- Acceptance Criteria: Tool supports:
  - import of MS Word HTML preserving structure of document sections and paragraphs and image attachments
  - pasting of a text or a HTML fragment to requirements description.
- As a(n): Editor
- I want to: import a requirements specification from a MS Word document
- So that: I can reuse existing requirements specifications or other structured documents
- Status: Verified
- Type: Requirement

#### NEEDS-71: Import from Excel (NEEDS Object Type)
- Acceptance Criteria: Tool supports:
  - import of new requirements from a CSV file including custom attribute values
  - updating requirements from a CSV file including custom attribute values
- As a(n): Editor
- I want to: import requirements from a MS Excel spreadsheet
- So that: I can import or update list of requirements
- Status: Verified
- Type: Requirement

#### NEEDS-28: Export to Word (NEEDS Object Type)
- Acceptance Criteria: Tool supports:
  - export of a document to a HTML file,
  - import of an exported HTML file to a MS Word document preserving requirements structure and content
- As a(n): Editor
- I want to: to export structured requirements specification to MS Word
- So that: I can share requirements specifications with users without the tool
- Status: Verified
- Type: Requirement

#### NEEDS-72: Export to CSV (NEEDS Object Type)
- Acceptance Criteria: Tool supports:
  - export of filtered list of requirements to a CSV file.
- As a(n): Editor
- I want to: export filtered list of requirements to MS Excel
- So that: I can reuse or update requirements in another application
- Status: Verified
- Type: Requirement

## NEEDS-4: Constraints (NEEDS Object Type)
- Type: Section

### NEEDS-39: Startup Time (NEEDS Object Type)
- Acceptance Criteria: Tool starts in less than 10s even for large projects.
- As a(n): Editor
- I want to: quickly start the tool
- So that: I do not need to wait long time for editing a project
- Status: Verified
- Type: Requirement

### NEEDS-41: Edit Response Time (NEEDS Object Type)
- Acceptance Criteria: Tool updates view after any edit operation in a document with 10000 requirements in less than 1s.
- As a(n): Editor
- I want to: edit effectively requirements in large documents
- So that: I can work without waiting for tool responses
- Status: Verified
- Type: Requirement

### NEEDS-44: Document Size (NEEDS Object Type)
- Acceptance Criteria: Tool can store documents with 10000 requirements and 100 attachments of total size 100 MB.
- As a(n): Editor
- I want to: create large requirements specifications
- So that: I can capture all requirements in a single document even for complex system development projects
- Status: Verified
- Type: Requirement

### NEEDS-42: Security (NEEDS Object Type)
- Acceptance Criteria: Tool does not send any project information to the internet without user consent.
- As a(n): Editor
- I want to: store confidential information in the tool
- So that: I can be sure that no confidential information is compromised
- Status: Verified
- Type: Requirement

### NEEDS-51: Compatibility (NEEDS Object Type)
- Acceptance Criteria: Tool is installed and run on Windows, Linux and a Mac.
- As a(n): Editor
- I want to: install and run the tool on Windows, Linux or Mac operating system
- So that: I can use the tool on any desktop PC or notebook.
- Status: Verified
- Type: Requirement

# Specification: ASVS
- ReqIF.Description: OWASP Application Security Verification Standard 4.0.3

## ASVS-61: Architecture, Design and Threat Modeling (ASVS Object Type)
- ASVS ID: 1
- Ordinal: 1
- Type: Section

### ASVS-62: Secure Software Development Lifecycle (ASVS Object Type)
- ASVS ID: 1.1
- Ordinal: 1
- Type: Section

#### ASVS-63 (ASVS Object Type)
Verify the use of a secure software development lifecycle that addresses security in all stages of development. (C1)
- Applicable: false
- ASVS ID: 1.1.1
- L1: Not required
- L2: Required
- L2 Text: ✓
- L3: Required
- L3 Text: ✓
- Ordinal: 1
- Type: Requirement

#### ASVS-64 (ASVS Object Type)
Verify the use of threat modeling for every design change or sprint planning to identify threats, plan for countermeasures, facilitate appropriate risk responses, and guide security testing.
- Applicable: false
- ASVS ID: 1.1.2
- CWE: 1053
- L1: Not required
- L2: Required
- L2 Text: ✓
- L3: Required
- L3 Text: ✓
- Ordinal: 2
- Type: Requirement

#### ASVS-65 (ASVS Object Type)
Verify that all user stories and features contain functional security constraints, such as "As a user, I should be able to view and edit my profile. I should not be able to view or edit anyone else's profile"
- Applicable: false
- ASVS ID: 1.1.3
- CWE: 1110
- L1: Not required
- L2: Required
- L2 Text: ✓
- L3: Required
- L3 Text: ✓
- Ordinal: 3
- Type: Requirement

#### ASVS-66 (ASVS Object Type)
Verify documentation and justification of all the application's trust boundaries, components, and significant data flows.
- Applicable: false
- ASVS ID: 1.1.4
- CWE: 1059
- L1: Not required
- L2: Required
- L2 Text: ✓
- L3: Required
- L3 Text: ✓
- Ordinal: 4
- Type: Requirement

#### ASVS-67 (ASVS Object Type)
Verify definition and security analysis of the application's high-level architecture and all connected remote services. (C1)
- Applicable: false
- ASVS ID: 1.1.5
- CWE: 1059
- L1: Not required
- L2: Required
- L2 Text: ✓
- L3: Required
- L3 Text: ✓
- Ordinal: 5
- Type: Requirement

#### ASVS-68 (ASVS Object Type)
Verify implementation of centralized, simple (economy of design), vetted, secure, and reusable security controls to avoid duplicate, missing, ineffective, or insecure controls. (C10)
- Applicable: false
- ASVS ID: 1.1.6
- CWE: 637
- L1: Not required
- L2: Required
- L2 Text: ✓
- L3: Required
- L3 Text: ✓
- Ordinal: 6
- Type: Requirement

#### ASVS-69 (ASVS Object Type)
Verify availability of a secure coding checklist, security requirements, guideline, or policy to all developers and testers.
- Applicable: false
- ASVS ID: 1.1.7
- CWE: 637
- L1: Not required
- L2: Required
- L2 Text: ✓
- L3: Required
- L3 Text: ✓
- Ordinal: 7
- Type: Requirement

### ASVS-70: Authentication Architecture (ASVS Object Type)
- ASVS ID: 1.2
- Ordinal: 2
- Type: Section

#### ASVS-71 (ASVS Object Type)
Verify the use of unique or special low-privilege operating system accounts for all application components, services, and servers. (C3)
- Applicable: false
- ASVS ID: 1.2.1
- CWE: 250
- L1: Not required
- L2: Required
- L2 Text: ✓
- L3: Required
- L3 Text: ✓
- Ordinal: 1
- Type: Requirement

#### ASVS-72 (ASVS Object Type)
Verify that communications between application components, including APIs, middleware and data layers, are authenticated. Components should have the least necessary privileges needed. (C3)
- Applicable: false
- ASVS ID: 1.2.2
- CWE: 306
- L1: Not required
- L2: Required
- L2 Text: ✓
- L3: Required
- L3 Text: ✓
- Ordinal: 2
- Type: Requirement

#### ASVS-73 (ASVS Object Type)
Verify that the application uses a single vetted authentication mechanism that is known to be secure, can be extended to include strong authentication, and has sufficient logging and monitoring to detect account abuse or breaches.
- Applicable: false
- ASVS ID: 1.2.3
- CWE: 306
- L1: Not required
- L2: Required
- L2 Text: ✓
- L3: Required
- L3 Text: ✓
- Ordinal: 3
- Type: Requirement

#### ASVS-74 (ASVS Object Type)
Verify that all authentication pathways and identity management APIs implement consistent authentication security control strength, such that there are no weaker alternatives per the risk of the application.
- Applicable: false
- ASVS ID: 1.2.4
- CWE: 306
- L1: Not required
- L2: Required
- L2 Text: ✓
- L3: Required
- L3 Text: ✓
- Ordinal: 4
- Type: Requirement

### ASVS-75: Session Management Architecture (ASVS Object Type)
- ASVS ID: 1.3
- Ordinal: 3
- Type: Section

### ASVS-76: Access Control Architecture (ASVS Object Type)
- ASVS ID: 1.4
- Ordinal: 4
- Type: Section

#### ASVS-77 (ASVS Object Type)
Verify that trusted enforcement points, such as access control gateways, servers, and serverless functions, enforce access controls. Never enforce access controls on the client.
- Applicable: false
- ASVS ID: 1.4.1
- CWE: 602
- L1: Not required
- L2: Required
- L2 Text: ✓
- L3: Required
- L3 Text: ✓
- Ordinal: 1
- Type: Requirement

#### ASVS-80 (ASVS Object Type)
Verify the application uses a single and well-vetted access control mechanism for accessing protected data and resources. All requests must pass through this single mechanism to avoid copy and paste or insecure alternative paths. (C7)
- Applicable: false
- ASVS ID: 1.4.4
- CWE: 284
- L1: Not required
- L2: Required
- L2 Text: ✓
- L3: Required
- L3 Text: ✓
- Ordinal: 4
- Type: Requirement

#### ASVS-81 (ASVS Object Type)
Verify that attribute or feature-based access control is used whereby the code checks the user's authorization for a feature/data item rather than just their role. Permissions should still be allocated using roles. (C7)
- Applicable: false
- ASVS ID: 1.4.5
- CWE: 275
- L1: Not required
- L2: Required
- L2 Text: ✓
- L3: Required
- L3 Text: ✓
- Ordinal: 5
- Type: Requirement

### ASVS-82: Input and Output Architecture (ASVS Object Type)
- ASVS ID: 1.5
- Ordinal: 5
- Type: Section

#### ASVS-83 (ASVS Object Type)
Verify that input and output requirements clearly define how to handle and process data based on type, content, and applicable laws, regulations, and other policy compliance.
- Applicable: false
- ASVS ID: 1.5.1
- CWE: 1029
- L1: Not required
- L2: Required
- L2 Text: ✓
- L3: Required
- L3 Text: ✓
- Ordinal: 1
- Type: Requirement

#### ASVS-84 (ASVS Object Type)
Verify that serialization is not used when communicating with untrusted clients. If this is not possible, ensure that adequate integrity controls (and possibly encryption if sensitive data is sent) are enforced to prevent deserialization attacks including object injection.
- Applicable: false
- ASVS ID: 1.5.2
- CWE: 502
- L1: Not required
- L2: Required
- L2 Text: ✓
- L3: Required
- L3 Text: ✓
- Ordinal: 2
- Type: Requirement

#### ASVS-85 (ASVS Object Type)
Verify that input validation is enforced on a trusted service layer. (C5)
- Applicable: false
- ASVS ID: 1.5.3
- CWE: 602
- L1: Not required
- L2: Required
- L2 Text: ✓
- L3: Required
- L3 Text: ✓
- Ordinal: 3
- Type: Requirement

#### ASVS-86 (ASVS Object Type)
Verify that output encoding occurs close to or by the interpreter for which it is intended. (C4)
- Applicable: false
- ASVS ID: 1.5.4
- CWE: 116
- L1: Not required
- L2: Required
- L2 Text: ✓
- L3: Required
- L3 Text: ✓
- Ordinal: 4
- Type: Requirement

### ASVS-87: Cryptographic Architecture (ASVS Object Type)
- ASVS ID: 1.6
- Ordinal: 6
- Type: Section

#### ASVS-88 (ASVS Object Type)
Verify that there is an explicit policy for management of cryptographic keys and that a cryptographic key lifecycle follows a key management standard such as NIST SP 800-57.
- Applicable: false
- ASVS ID: 1.6.1
- CWE: 320
- L1: Not required
- L2: Required
- L2 Text: ✓
- L3: Required
- L3 Text: ✓
- Ordinal: 1
- Type: Requirement

#### ASVS-89 (ASVS Object Type)
Verify that consumers of cryptographic services protect key material and other secrets by using key vaults or API based alternatives.
- Applicable: false
- ASVS ID: 1.6.2
- CWE: 320
- L1: Not required
- L2: Required
- L2 Text: ✓
- L3: Required
- L3 Text: ✓
- Ordinal: 2
- Type: Requirement

#### ASVS-90 (ASVS Object Type)
Verify that all keys and passwords are replaceable and are part of a well-defined process to re-encrypt sensitive data.
- Applicable: false
- ASVS ID: 1.6.3
- CWE: 320
- L1: Not required
- L2: Required
- L2 Text: ✓
- L3: Required
- L3 Text: ✓
- Ordinal: 3
- Type: Requirement

#### ASVS-91 (ASVS Object Type)
Verify that the architecture treats client-side secrets--such as symmetric keys, passwords, or API tokens--as insecure and never uses them to protect or access sensitive data.
- Applicable: false
- ASVS ID: 1.6.4
- CWE: 320
- L1: Not required
- L2: Required
- L2 Text: ✓
- L3: Required
- L3 Text: ✓
- Ordinal: 4
- Type: Requirement

### ASVS-92: Errors, Logging and Auditing Architecture (ASVS Object Type)
- ASVS ID: 1.7
- Ordinal: 7
- Type: Section

#### ASVS-93 (ASVS Object Type)
Verify that a common logging format and approach is used across the system. (C9)
- Applicable: false
- ASVS ID: 1.7.1
- CWE: 1009
- L1: Not required
- L2: Required
- L2 Text: ✓
- L3: Required
- L3 Text: ✓
- Ordinal: 1
- Type: Requirement

#### ASVS-94 (ASVS Object Type)
Verify that logs are securely transmitted to a preferably remote system for analysis, detection, alerting, and escalation. (C9)
- Applicable: false
- ASVS ID: 1.7.2
- L1: Not required
- L2: Required
- L2 Text: ✓
- L3: Required
- L3 Text: ✓
- Ordinal: 2
- Type: Requirement

### ASVS-95: Data Protection and Privacy Architecture (ASVS Object Type)
- ASVS ID: 1.8
- Ordinal: 8
- Type: Section

#### ASVS-96 (ASVS Object Type)
Verify that all sensitive data is identified and classified into protection levels.
- Applicable: false
- ASVS ID: 1.8.1
- L1: Not required
- L2: Required
- L2 Text: ✓
- L3: Required
- L3 Text: ✓
- Ordinal: 1
- Type: Requirement

#### ASVS-97 (ASVS Object Type)
Verify that all protection levels have an associated set of protection requirements, such as encryption requirements, integrity requirements, retention, privacy and other confidentiality requirements, and that these are applied in the architecture.
- Applicable: false
- ASVS ID: 1.8.2
- L1: Not required
- L2: Required
- L2 Text: ✓
- L3: Required
- L3 Text: ✓
- Ordinal: 2
- Type: Requirement

### ASVS-98: Communications Architecture (ASVS Object Type)
- ASVS ID: 1.9
- Ordinal: 9
- Type: Section

#### ASVS-99 (ASVS Object Type)
Verify the application encrypts communications between components, particularly when these components are in different containers, systems, sites, or cloud providers. (C3)
- Applicable: false
- ASVS ID: 1.9.1
- CWE: 319
- L1: Not required
- L2: Required
- L2 Text: ✓
- L3: Required
- L3 Text: ✓
- Ordinal: 1
- Type: Requirement

#### ASVS-100 (ASVS Object Type)
Verify that application components verify the authenticity of each side in a communication link to prevent person-in-the-middle attacks. For example, application components should validate TLS certificates and chains.
- Applicable: false
- ASVS ID: 1.9.2
- CWE: 295
- L1: Not required
- L2: Required
- L2 Text: ✓
- L3: Required
- L3 Text: ✓
- Ordinal: 2
- Type: Requirement

### ASVS-101: Malicious Software Architecture (ASVS Object Type)
- ASVS ID: 1.10
- Ordinal: 10
- Type: Section

#### ASVS-102 (ASVS Object Type)
Verify that a source code control system is in use, with procedures to ensure that check-ins are accompanied by issues or change tickets. The source code control system should have access control and identifiable users to allow traceability of any changes.
- Applicable: false
- ASVS ID: 1.10.1
- CWE: 284
- L1: Not required
- L2: Required
- L2 Text: ✓
- L3: Required
- L3 Text: ✓
- Ordinal: 1
- Type: Requirement

### ASVS-103: Business Logic Architecture (ASVS Object Type)
- ASVS ID: 1.11
- Ordinal: 11
- Type: Section

#### ASVS-104 (ASVS Object Type)
Verify the definition and documentation of all application components in terms of the business or security functions they provide.
- Applicable: false
- ASVS ID: 1.11.1
- CWE: 1059
- L1: Not required
- L2: Required
- L2 Text: ✓
- L3: Required
- L3 Text: ✓
- Ordinal: 1
- Type: Requirement

#### ASVS-105 (ASVS Object Type)
Verify that all high-value business logic flows, including authentication, session management and access control, do not share unsynchronized state.
- Applicable: false
- ASVS ID: 1.11.2
- CWE: 362
- L1: Not required
- L2: Required
- L2 Text: ✓
- L3: Required
- L3 Text: ✓
- Ordinal: 2
- Type: Requirement

#### ASVS-106 (ASVS Object Type)
Verify that all high-value business logic flows, including authentication, session management and access control are thread safe and resistant to time-of-check and time-of-use race conditions.
- Applicable: false
- ASVS ID: 1.11.3
- CWE: 367
- L1: Not required
- L2: Not required
- L3: Required
- L3 Text: ✓
- Ordinal: 3
- Type: Requirement

### ASVS-107: Secure File Upload Architecture (ASVS Object Type)
- ASVS ID: 1.12
- Ordinal: 12
- Type: Section

#### ASVS-109 (ASVS Object Type)
Verify that user-uploaded files - if required to be displayed or downloaded from the application - are served by either octet stream downloads, or from an unrelated domain, such as a cloud file storage bucket. Implement a suitable Content Security Policy (CSP) to reduce the risk from XSS vectors or other attacks from the uploaded file.
- Applicable: false
- ASVS ID: 1.12.2
- CWE: 646
- L1: Not required
- L2: Required
- L2 Text: ✓
- L3: Required
- L3 Text: ✓
- Ordinal: 2
- Type: Requirement

### ASVS-110: API Architecture (ASVS Object Type)
- ASVS ID: 1.13
- Ordinal: 13
- Type: Section

### ASVS-111: Configuration Architecture (ASVS Object Type)
- ASVS ID: 1.14
- Ordinal: 14
- Type: Section

#### ASVS-112 (ASVS Object Type)
Verify the segregation of components of differing trust levels through well-defined security controls, firewall rules, API gateways, reverse proxies, cloud-based security groups, or similar mechanisms.
- Applicable: false
- ASVS ID: 1.14.1
- CWE: 923
- L1: Not required
- L2: Required
- L2 Text: ✓
- L3: Required
- L3 Text: ✓
- Ordinal: 1
- Type: Requirement

#### ASVS-113 (ASVS Object Type)
Verify that binary signatures, trusted connections, and verified endpoints are used to deploy binaries to remote devices.
- Applicable: false
- ASVS ID: 1.14.2
- CWE: 494
- L1: Not required
- L2: Required
- L2 Text: ✓
- L3: Required
- L3 Text: ✓
- Ordinal: 2
- Type: Requirement

#### ASVS-114 (ASVS Object Type)
Verify that the build pipeline warns of out-of-date or insecure components and takes appropriate actions.
- Applicable: false
- ASVS ID: 1.14.3
- CWE: 1104
- L1: Not required
- L2: Required
- L2 Text: ✓
- L3: Required
- L3 Text: ✓
- Ordinal: 3
- Type: Requirement

#### ASVS-115 (ASVS Object Type)
Verify that the build pipeline contains a build step to automatically build and verify the secure deployment of the application, particularly if the application infrastructure is software defined, such as cloud environment build scripts.
- Applicable: false
- ASVS ID: 1.14.4
- L1: Not required
- L2: Required
- L2 Text: ✓
- L3: Required
- L3 Text: ✓
- Ordinal: 4
- Type: Requirement

#### ASVS-116 (ASVS Object Type)
Verify that application deployments adequately sandbox, containerize and/or isolate at the network level to delay and deter attackers from attacking other applications, especially when they are performing sensitive or dangerous actions such as deserialization. (C5)
- Applicable: false
- ASVS ID: 1.14.5
- CWE: 265
- L1: Not required
- L2: Required
- L2 Text: ✓
- L3: Required
- L3 Text: ✓
- Ordinal: 5
- Type: Requirement

#### ASVS-117 (ASVS Object Type)
Verify the application does not use unsupported, insecure, or deprecated client-side technologies such as NSAPI plugins, Flash, Shockwave, ActiveX, Silverlight, NACL, or client-side Java applets.
- Applicable: false
- ASVS ID: 1.14.6
- CWE: 477
- L1: Not required
- L2: Required
- L2 Text: ✓
- L3: Required
- L3 Text: ✓
- Ordinal: 6
- Type: Requirement

## ASVS-118: Authentication (ASVS Object Type)
- ASVS ID: 2
- Ordinal: 2
- Type: Section

### ASVS-119: Password Security (ASVS Object Type)
- ASVS ID: 2.1
- Ordinal: 1
- Type: Section

#### ASVS-120 (ASVS Object Type)
Verify that user set passwords are at least 12 characters in length (after multiple spaces are combined). (C6)
- Applicable: false
- ASVS ID: 2.1.1
- CWE: 521
- L1: Required
- L1 Text: ✓
- L2: Required
- L2 Text: ✓
- L3: Required
- L3 Text: ✓
- NIST §: 5.1.1.2
- Ordinal: 1
- Type: Requirement

#### ASVS-121 (ASVS Object Type)
Verify that passwords of at least 64 characters are permitted, and that passwords of more than 128 characters are denied. (C6)
- Applicable: false
- ASVS ID: 2.1.2
- CWE: 521
- L1: Required
- L1 Text: ✓
- L2: Required
- L2 Text: ✓
- L3: Required
- L3 Text: ✓
- NIST §: 5.1.1.2
- Ordinal: 2
- Type: Requirement

#### ASVS-122 (ASVS Object Type)
Verify that password truncation is not performed. However, consecutive multiple spaces may be replaced by a single space. (C6)
- Applicable: false
- ASVS ID: 2.1.3
- CWE: 521
- L1: Required
- L1 Text: ✓
- L2: Required
- L2 Text: ✓
- L3: Required
- L3 Text: ✓
- NIST §: 5.1.1.2
- Ordinal: 3
- Type: Requirement

#### ASVS-123 (ASVS Object Type)
Verify that any printable Unicode character, including language neutral characters such as spaces and Emojis are permitted in passwords.
- Applicable: false
- ASVS ID: 2.1.4
- CWE: 521
- L1: Required
- L1 Text: ✓
- L2: Required
- L2 Text: ✓
- L3: Required
- L3 Text: ✓
- NIST §: 5.1.1.2
- Ordinal: 4
- Type: Requirement

#### ASVS-124 (ASVS Object Type)
Verify users can change their password.
- Applicable: false
- ASVS ID: 2.1.5
- CWE: 620
- L1: Required
- L1 Text: ✓
- L2: Required
- L2 Text: ✓
- L3: Required
- L3 Text: ✓
- NIST §: 5.1.1.2
- Ordinal: 5
- Type: Requirement

#### ASVS-125 (ASVS Object Type)
Verify that password change functionality requires the user's current and new password.
- Applicable: false
- ASVS ID: 2.1.6
- CWE: 620
- L1: Required
- L1 Text: ✓
- L2: Required
- L2 Text: ✓
- L3: Required
- L3 Text: ✓
- NIST §: 5.1.1.2
- Ordinal: 6
- Type: Requirement

#### ASVS-126 (ASVS Object Type)
Verify that passwords submitted during account registration, login, and password change are checked against a set of breached passwords either locally (such as the top 1,000 or 10,000 most common passwords which match the system's password policy) or using an external API. If using an API a zero knowledge proof or other mechanism should be used to ensure that the plain text password is not sent or used in verifying the breach status of the password. If the password is breached, the application must require the user to set a new non-breached password. (C6)
- Applicable: false
- ASVS ID: 2.1.7
- CWE: 521
- L1: Required
- L1 Text: ✓
- L2: Required
- L2 Text: ✓
- L3: Required
- L3 Text: ✓
- NIST §: 5.1.1.2
- Ordinal: 7
- Type: Requirement

#### ASVS-127 (ASVS Object Type)
Verify that a password strength meter is provided to help users set a stronger password.
- Applicable: false
- ASVS ID: 2.1.8
- CWE: 521
- L1: Required
- L1 Text: ✓
- L2: Required
- L2 Text: ✓
- L3: Required
- L3 Text: ✓
- NIST §: 5.1.1.2
- Ordinal: 8
- Type: Requirement

#### ASVS-128 (ASVS Object Type)
Verify that there are no password composition rules limiting the type of characters permitted. There should be no requirement for upper or lower case or numbers or special characters. (C6)
- Applicable: false
- ASVS ID: 2.1.9
- CWE: 521
- L1: Required
- L1 Text: ✓
- L2: Required
- L2 Text: ✓
- L3: Required
- L3 Text: ✓
- NIST §: 5.1.1.2
- Ordinal: 9
- Type: Requirement

#### ASVS-129 (ASVS Object Type)
Verify that there are no periodic credential rotation or password history requirements.
- Applicable: false
- ASVS ID: 2.1.10
- CWE: 263
- L1: Required
- L1 Text: ✓
- L2: Required
- L2 Text: ✓
- L3: Required
- L3 Text: ✓
- NIST §: 5.1.1.2
- Ordinal: 10
- Type: Requirement

#### ASVS-130 (ASVS Object Type)
Verify that "paste" functionality, browser password helpers, and external password managers are permitted.
- Applicable: false
- ASVS ID: 2.1.11
- CWE: 521
- L1: Required
- L1 Text: ✓
- L2: Required
- L2 Text: ✓
- L3: Required
- L3 Text: ✓
- NIST §: 5.1.1.2
- Ordinal: 11
- Type: Requirement

#### ASVS-131 (ASVS Object Type)
Verify that the user can choose to either temporarily view the entire masked password, or temporarily view the last typed character of the password on platforms that do not have this as built-in functionality.
- Applicable: false
- ASVS ID: 2.1.12
- CWE: 521
- L1: Required
- L1 Text: ✓
- L2: Required
- L2 Text: ✓
- L3: Required
- L3 Text: ✓
- NIST §: 5.1.1.2
- Ordinal: 12
- Type: Requirement

### ASVS-132: General Authenticator Security (ASVS Object Type)
- ASVS ID: 2.2
- Ordinal: 2
- Type: Section

#### ASVS-133 (ASVS Object Type)
Verify that anti-automation controls are effective at mitigating breached credential testing, brute force, and account lockout attacks. Such controls include blocking the most common breached passwords, soft lockouts, rate limiting, CAPTCHA, ever increasing delays between attempts, IP address restrictions, or risk-based restrictions such as location, first login on a device, recent attempts to unlock the account, or similar. Verify that no more than 100 failed attempts per hour is possible on a single account.
- Applicable: false
- ASVS ID: 2.2.1
- CWE: 307
- L1: Required
- L1 Text: ✓
- L2: Required
- L2 Text: ✓
- L3: Required
- L3 Text: ✓
- NIST §: 5.2.2 / 5.1.1.2 / 5.1.4.2 / 5.1.5.2
- Ordinal: 1
- Type: Requirement

#### ASVS-134 (ASVS Object Type)
Verify that the use of weak authenticators (such as SMS and email) is limited to secondary verification and transaction approval and not as a replacement for more secure authentication methods. Verify that stronger methods are offered before weak methods, users are aware of the risks, or that proper measures are in place to limit the risks of account compromise.
- Applicable: false
- ASVS ID: 2.2.2
- CWE: 304
- L1: Required
- L1 Text: ✓
- L2: Required
- L2 Text: ✓
- L3: Required
- L3 Text: ✓
- NIST §: 5.2.10
- Ordinal: 2
- Type: Requirement

#### ASVS-135 (ASVS Object Type)
Verify that secure notifications are sent to users after updates to authentication details, such as credential resets, email or address changes, logging in from unknown or risky locations. The use of push notifications - rather than SMS or email - is preferred, but in the absence of push notifications, SMS or email is acceptable as long as no sensitive information is disclosed in the notification.
- Applicable: false
- ASVS ID: 2.2.3
- CWE: 620
- L1: Required
- L1 Text: ✓
- L2: Required
- L2 Text: ✓
- L3: Required
- L3 Text: ✓
- Ordinal: 3
- Type: Requirement

#### ASVS-136 (ASVS Object Type)
Verify impersonation resistance against phishing, such as the use of multi-factor authentication, cryptographic devices with intent (such as connected keys with a push to authenticate), or at higher AAL levels, client-side certificates.
- Applicable: false
- ASVS ID: 2.2.4
- CWE: 308
- L1: Not required
- L2: Not required
- L3: Required
- L3 Text: ✓
- NIST §: 5.2.5
- Ordinal: 4
- Type: Requirement

#### ASVS-137 (ASVS Object Type)
Verify that where a Credential Service Provider (CSP) and the application verifying authentication are separated, mutually authenticated TLS is in place between the two endpoints.
- Applicable: false
- ASVS ID: 2.2.5
- CWE: 319
- L1: Not required
- L2: Not required
- L3: Required
- L3 Text: ✓
- NIST §: 5.2.6
- Ordinal: 5
- Type: Requirement

#### ASVS-138 (ASVS Object Type)
Verify replay resistance through the mandated use of One-time Passwords (OTP) devices, cryptographic authenticators, or lookup codes.
- Applicable: false
- ASVS ID: 2.2.6
- CWE: 308
- L1: Not required
- L2: Not required
- L3: Required
- L3 Text: ✓
- NIST §: 5.2.8
- Ordinal: 6
- Type: Requirement

#### ASVS-139 (ASVS Object Type)
Verify intent to authenticate by requiring the entry of an OTP token or user-initiated action such as a button press on a FIDO hardware key.
- Applicable: false
- ASVS ID: 2.2.7
- CWE: 308
- L1: Not required
- L2: Not required
- L3: Required
- L3 Text: ✓
- NIST §: 5.2.9
- Ordinal: 7
- Type: Requirement

### ASVS-140: Authenticator Lifecycle (ASVS Object Type)
- ASVS ID: 2.3
- Ordinal: 3
- Type: Section

#### ASVS-141 (ASVS Object Type)
Verify system generated initial passwords or activation codes SHOULD be securely randomly generated, SHOULD be at least 6 characters long, and MAY contain letters and numbers, and expire after a short period of time. These initial secrets must not be permitted to become the long term password.
- Applicable: false
- ASVS ID: 2.3.1
- CWE: 330
- L1: Required
- L1 Text: ✓
- L2: Required
- L2 Text: ✓
- L3: Required
- L3 Text: ✓
- NIST §: 5.1.1.2 / A.3
- Ordinal: 1
- Type: Requirement

#### ASVS-142 (ASVS Object Type)
Verify that enrollment and use of user-provided authentication devices are supported, such as a U2F or FIDO tokens.
- Applicable: false
- ASVS ID: 2.3.2
- CWE: 308
- L1: Not required
- L2: Required
- L2 Text: ✓
- L3: Required
- L3 Text: ✓
- NIST §: 6.1.3
- Ordinal: 2
- Type: Requirement

#### ASVS-143 (ASVS Object Type)
Verify that renewal instructions are sent with sufficient time to renew time bound authenticators.
- Applicable: false
- ASVS ID: 2.3.3
- CWE: 287
- L1: Not required
- L2: Required
- L2 Text: ✓
- L3: Required
- L3 Text: ✓
- NIST §: 6.1.4
- Ordinal: 3
- Type: Requirement

### ASVS-144: Credential Storage (ASVS Object Type)
- ASVS ID: 2.4
- Ordinal: 4
- Type: Section

#### ASVS-145 (ASVS Object Type)
Verify that passwords are stored in a form that is resistant to offline attacks. Passwords SHALL be salted and hashed using an approved one-way key derivation or password hashing function. Key derivation and password hashing functions take a password, a salt, and a cost factor as inputs when generating a password hash. (C6)
- Applicable: false
- ASVS ID: 2.4.1
- CWE: 916
- L1: Not required
- L2: Required
- L2 Text: ✓
- L3: Required
- L3 Text: ✓
- NIST §: 5.1.1.2
- Ordinal: 1
- Type: Requirement

#### ASVS-146 (ASVS Object Type)
Verify that the salt is at least 32 bits in length and be chosen arbitrarily to minimize salt value collisions among stored hashes. For each credential, a unique salt value and the resulting hash SHALL be stored. (C6)
- Applicable: false
- ASVS ID: 2.4.2
- CWE: 916
- L1: Not required
- L2: Required
- L2 Text: ✓
- L3: Required
- L3 Text: ✓
- NIST §: 5.1.1.2
- Ordinal: 2
- Type: Requirement

#### ASVS-147 (ASVS Object Type)
Verify that if PBKDF2 is used, the iteration count SHOULD be as large as verification server performance will allow, typically at least 100,000 iterations. (C6)
- Applicable: false
- ASVS ID: 2.4.3
- CWE: 916
- L1: Not required
- L2: Required
- L2 Text: ✓
- L3: Required
- L3 Text: ✓
- NIST §: 5.1.1.2
- Ordinal: 3
- Type: Requirement

#### ASVS-148 (ASVS Object Type)
Verify that if bcrypt is used, the work factor SHOULD be as large as verification server performance will allow, with a minimum of 10. (C6)
- Applicable: false
- ASVS ID: 2.4.4
- CWE: 916
- L1: Not required
- L2: Required
- L2 Text: ✓
- L3: Required
- L3 Text: ✓
- NIST §: 5.1.1.2
- Ordinal: 4
- Type: Requirement

#### ASVS-149 (ASVS Object Type)
Verify that an additional iteration of a key derivation function is performed, using a salt value that is secret and known only to the verifier. Generate the salt value using an approved random bit generator [SP 800-90Ar1] and provide at least the minimum security strength specified in the latest revision of SP 800-131A. The secret salt value SHALL be stored separately from the hashed passwords (e.g., in a specialized device like a hardware security module).
- Applicable: false
- ASVS ID: 2.4.5
- CWE: 916
- L1: Not required
- L2: Required
- L2 Text: ✓
- L3: Required
- L3 Text: ✓
- NIST §: 5.1.1.2
- Ordinal: 5
- Type: Requirement

### ASVS-150: Credential Recovery (ASVS Object Type)
- ASVS ID: 2.5
- Ordinal: 5
- Type: Section

#### ASVS-151 (ASVS Object Type)
Verify that a system generated initial activation or recovery secret is not sent in clear text to the user. (C6)
- Applicable: false
- ASVS ID: 2.5.1
- CWE: 640
- L1: Required
- L1 Text: ✓
- L2: Required
- L2 Text: ✓
- L3: Required
- L3 Text: ✓
- NIST §: 5.1.1.2
- Ordinal: 1
- Type: Requirement

#### ASVS-152 (ASVS Object Type)
Verify password hints or knowledge-based authentication (so-called "secret questions") are not present.
- Applicable: false
- ASVS ID: 2.5.2
- CWE: 640
- L1: Required
- L1 Text: ✓
- L2: Required
- L2 Text: ✓
- L3: Required
- L3 Text: ✓
- NIST §: 5.1.1.2
- Ordinal: 2
- Type: Requirement

#### ASVS-153 (ASVS Object Type)
Verify password credential recovery does not reveal the current password in any way. (C6)
- Applicable: false
- ASVS ID: 2.5.3
- CWE: 640
- L1: Required
- L1 Text: ✓
- L2: Required
- L2 Text: ✓
- L3: Required
- L3 Text: ✓
- NIST §: 5.1.1.2
- Ordinal: 3
- Type: Requirement

#### ASVS-154 (ASVS Object Type)
Verify shared or default accounts are not present (e.g. "root", "admin", or "sa").
- Applicable: false
- ASVS ID: 2.5.4
- CWE: 16
- L1: Required
- L1 Text: ✓
- L2: Required
- L2 Text: ✓
- L3: Required
- L3 Text: ✓
- NIST §: 5.1.1.2 / A.3
- Ordinal: 4
- Type: Requirement

#### ASVS-155 (ASVS Object Type)
Verify that if an authentication factor is changed or replaced, that the user is notified of this event.
- Applicable: false
- ASVS ID: 2.5.5
- CWE: 304
- L1: Required
- L1 Text: ✓
- L2: Required
- L2 Text: ✓
- L3: Required
- L3 Text: ✓
- NIST §: 6.1.2.3
- Ordinal: 5
- Type: Requirement

#### ASVS-156 (ASVS Object Type)
Verify forgotten password, and other recovery paths use a secure recovery mechanism, such as time-based OTP (TOTP) or other soft token, mobile push, or another offline recovery mechanism. (C6)
- Applicable: false
- ASVS ID: 2.5.6
- CWE: 640
- L1: Required
- L1 Text: ✓
- L2: Required
- L2 Text: ✓
- L3: Required
- L3 Text: ✓
- NIST §: 5.1.1.2
- Ordinal: 6
- Type: Requirement

#### ASVS-157 (ASVS Object Type)
Verify that if OTP or multi-factor authentication factors are lost, that evidence of identity proofing is performed at the same level as during enrollment.
- Applicable: false
- ASVS ID: 2.5.7
- CWE: 308
- L1: Not required
- L2: Required
- L2 Text: ✓
- L3: Required
- L3 Text: ✓
- NIST §: 6.1.2.3
- Ordinal: 7
- Type: Requirement

### ASVS-158: Look-up Secret Verifier (ASVS Object Type)
- ASVS ID: 2.6
- Ordinal: 6
- Type: Section

#### ASVS-159 (ASVS Object Type)
Verify that lookup secrets can be used only once.
- Applicable: false
- ASVS ID: 2.6.1
- CWE: 308
- L1: Not required
- L2: Required
- L2 Text: ✓
- L3: Required
- L3 Text: ✓
- NIST §: 5.1.2.2
- Ordinal: 1
- Type: Requirement

#### ASVS-160 (ASVS Object Type)
Verify that lookup secrets have sufficient randomness (112 bits of entropy), or if less than 112 bits of entropy, salted with a unique and random 32-bit salt and hashed with an approved one-way hash.
- Applicable: false
- ASVS ID: 2.6.2
- CWE: 330
- L1: Not required
- L2: Required
- L2 Text: ✓
- L3: Required
- L3 Text: ✓
- NIST §: 5.1.2.2
- Ordinal: 2
- Type: Requirement

#### ASVS-161 (ASVS Object Type)
Verify that lookup secrets are resistant to offline attacks, such as predictable values.
- Applicable: false
- ASVS ID: 2.6.3
- CWE: 310
- L1: Not required
- L2: Required
- L2 Text: ✓
- L3: Required
- L3 Text: ✓
- NIST §: 5.1.2.2
- Ordinal: 3
- Type: Requirement

### ASVS-162: Out of Band Verifier (ASVS Object Type)
- ASVS ID: 2.7
- Ordinal: 7
- Type: Section

#### ASVS-163 (ASVS Object Type)
Verify that clear text out of band (NIST "restricted") authenticators, such as SMS or PSTN, are not offered by default, and stronger alternatives such as push notifications are offered first.
- Applicable: false
- ASVS ID: 2.7.1
- CWE: 287
- L1: Required
- L1 Text: ✓
- L2: Required
- L2 Text: ✓
- L3: Required
- L3 Text: ✓
- NIST §: 5.1.3.2
- Ordinal: 1
- Type: Requirement

#### ASVS-164 (ASVS Object Type)
Verify that the out of band verifier expires out of band authentication requests, codes, or tokens after 10 minutes.
- Applicable: false
- ASVS ID: 2.7.2
- CWE: 287
- L1: Required
- L1 Text: ✓
- L2: Required
- L2 Text: ✓
- L3: Required
- L3 Text: ✓
- NIST §: 5.1.3.2
- Ordinal: 2
- Type: Requirement

#### ASVS-165 (ASVS Object Type)
Verify that the out of band verifier authentication requests, codes, or tokens are only usable once, and only for the original authentication request.
- Applicable: false
- ASVS ID: 2.7.3
- CWE: 287
- L1: Required
- L1 Text: ✓
- L2: Required
- L2 Text: ✓
- L3: Required
- L3 Text: ✓
- NIST §: 5.1.3.2
- Ordinal: 3
- Type: Requirement

#### ASVS-166 (ASVS Object Type)
Verify that the out of band authenticator and verifier communicates over a secure independent channel.
- Applicable: false
- ASVS ID: 2.7.4
- CWE: 523
- L1: Required
- L1 Text: ✓
- L2: Required
- L2 Text: ✓
- L3: Required
- L3 Text: ✓
- NIST §: 5.1.3.2
- Ordinal: 4
- Type: Requirement

#### ASVS-167 (ASVS Object Type)
Verify that the out of band verifier retains only a hashed version of the authentication code.
- Applicable: false
- ASVS ID: 2.7.5
- CWE: 256
- L1: Not required
- L2: Required
- L2 Text: ✓
- L3: Required
- L3 Text: ✓
- NIST §: 5.1.3.2
- Ordinal: 5
- Type: Requirement

#### ASVS-168 (ASVS Object Type)
Verify that the initial authentication code is generated by a secure random number generator, containing at least 20 bits of entropy (typically a six digital random number is sufficient).
- Applicable: false
- ASVS ID: 2.7.6
- CWE: 310
- L1: Not required
- L2: Required
- L2 Text: ✓
- L3: Required
- L3 Text: ✓
- NIST §: 5.1.3.2
- Ordinal: 6
- Type: Requirement

### ASVS-169: One Time Verifier (ASVS Object Type)
- ASVS ID: 2.8
- Ordinal: 8
- Type: Section

#### ASVS-170 (ASVS Object Type)
Verify that time-based OTPs have a defined lifetime before expiring.
- Applicable: false
- ASVS ID: 2.8.1
- CWE: 613
- L1: Required
- L1 Text: ✓
- L2: Required
- L2 Text: ✓
- L3: Required
- L3 Text: ✓
- NIST §: 5.1.4.2 / 5.1.5.2
- Ordinal: 1
- Type: Requirement

#### ASVS-171 (ASVS Object Type)
Verify that symmetric keys used to verify submitted OTPs are highly protected, such as by using a hardware security module or secure operating system based key storage.
- Applicable: false
- ASVS ID: 2.8.2
- CWE: 320
- L1: Not required
- L2: Required
- L2 Text: ✓
- L3: Required
- L3 Text: ✓
- NIST §: 5.1.4.2 / 5.1.5.2
- Ordinal: 2
- Type: Requirement

#### ASVS-172 (ASVS Object Type)
Verify that approved cryptographic algorithms are used in the generation, seeding, and verification of OTPs.
- Applicable: false
- ASVS ID: 2.8.3
- CWE: 326
- L1: Not required
- L2: Required
- L2 Text: ✓
- L3: Required
- L3 Text: ✓
- NIST §: 5.1.4.2 / 5.1.5.2
- Ordinal: 3
- Type: Requirement

#### ASVS-173 (ASVS Object Type)
Verify that time-based OTP can be used only once within the validity period.
- Applicable: false
- ASVS ID: 2.8.4
- CWE: 287
- L1: Not required
- L2: Required
- L2 Text: ✓
- L3: Required
- L3 Text: ✓
- NIST §: 5.1.4.2 / 5.1.5.2
- Ordinal: 4
- Type: Requirement

#### ASVS-174 (ASVS Object Type)
Verify that if a time-based multi-factor OTP token is re-used during the validity period, it is logged and rejected with secure notifications being sent to the holder of the device.
- Applicable: false
- ASVS ID: 2.8.5
- CWE: 287
- L1: Not required
- L2: Required
- L2 Text: ✓
- L3: Required
- L3 Text: ✓
- NIST §: 5.1.5.2
- Ordinal: 5
- Type: Requirement

#### ASVS-175 (ASVS Object Type)
Verify physical single-factor OTP generator can be revoked in case of theft or other loss. Ensure that revocation is immediately effective across logged in sessions, regardless of location.
- Applicable: false
- ASVS ID: 2.8.6
- CWE: 613
- L1: Not required
- L2: Required
- L2 Text: ✓
- L3: Required
- L3 Text: ✓
- NIST §: 5.2.1
- Ordinal: 6
- Type: Requirement

#### ASVS-176 (ASVS Object Type)
Verify that biometric authenticators are limited to use only as secondary factors in conjunction with either something you have and something you know.
- Applicable: false
- ASVS ID: 2.8.7
- CWE: 308
- L1: Not required
- L2: Recommended, but not required
- L2 Text: o
- L3: Required
- L3 Text: ✓
- NIST §: 5.2.3
- Ordinal: 7
- Type: Requirement

### ASVS-177: Cryptographic Verifier (ASVS Object Type)
- ASVS ID: 2.9
- Ordinal: 9
- Type: Section

#### ASVS-178 (ASVS Object Type)
Verify that cryptographic keys used in verification are stored securely and protected against disclosure, such as using a Trusted Platform Module (TPM) or Hardware Security Module (HSM), or an OS service that can use this secure storage.
- Applicable: false
- ASVS ID: 2.9.1
- CWE: 320
- L1: Not required
- L2: Required
- L2 Text: ✓
- L3: Required
- L3 Text: ✓
- NIST §: 5.1.7.2
- Ordinal: 1
- Type: Requirement

#### ASVS-179 (ASVS Object Type)
Verify that the challenge nonce is at least 64 bits in length, and statistically unique or unique over the lifetime of the cryptographic device.
- Applicable: false
- ASVS ID: 2.9.2
- CWE: 330
- L1: Not required
- L2: Required
- L2 Text: ✓
- L3: Required
- L3 Text: ✓
- NIST §: 5.1.7.2
- Ordinal: 2
- Type: Requirement

#### ASVS-180 (ASVS Object Type)
Verify that approved cryptographic algorithms are used in the generation, seeding, and verification.
- Applicable: false
- ASVS ID: 2.9.3
- CWE: 327
- L1: Not required
- L2: Required
- L2 Text: ✓
- L3: Required
- L3 Text: ✓
- NIST §: 5.1.7.2
- Ordinal: 3
- Type: Requirement

### ASVS-181: Service Authentication (ASVS Object Type)
- ASVS ID: 2.10
- Ordinal: 10
- Type: Section

#### ASVS-182 (ASVS Object Type)
Verify that intra-service secrets do not rely on unchanging credentials such as passwords, API keys or shared accounts with privileged access.
- Applicable: false
- ASVS ID: 2.10.1
- CWE: 287
- L1: Not required
- L2: Required
- L2 Text: OS assisted
- L3: Required
- L3 Text: HSM
- NIST §: 5.1.1.1
- Ordinal: 1
- Type: Requirement

#### ASVS-183 (ASVS Object Type)
Verify that if passwords are required for service authentication, the service account used is not a default credential. (e.g. root/root or admin/admin are default in some services during installation).
- Applicable: false
- ASVS ID: 2.10.2
- CWE: 255
- L1: Not required
- L2: Required
- L2 Text: OS assisted
- L3: Required
- L3 Text: HSM
- NIST §: 5.1.1.1
- Ordinal: 2
- Type: Requirement

#### ASVS-184 (ASVS Object Type)
Verify that passwords are stored with sufficient protection to prevent offline recovery attacks, including local system access.
- Applicable: false
- ASVS ID: 2.10.3
- CWE: 522
- L1: Not required
- L2: Required
- L2 Text: OS assisted
- L3: Required
- L3 Text: HSM
- NIST §: 5.1.1.1
- Ordinal: 3
- Type: Requirement

#### ASVS-185 (ASVS Object Type)
Verify passwords, integrations with databases and third-party systems, seeds and internal secrets, and API keys are managed securely and not included in the source code or stored within source code repositories. Such storage SHOULD resist offline attacks. The use of a secure software key store (L1), hardware TPM, or an HSM (L3) is recommended for password storage.
- Applicable: false
- ASVS ID: 2.10.4
- CWE: 798
- L1: Not required
- L2: Required
- L2 Text: OS assisted
- L3: Required
- L3 Text: HSM
- Ordinal: 4
- Type: Requirement

## ASVS-186: Session Management (ASVS Object Type)
- ASVS ID: 3
- Ordinal: 3
- Type: Section

### ASVS-187: Fundamental Session Management Security (ASVS Object Type)
- ASVS ID: 3.1
- Ordinal: 1
- Type: Section

#### ASVS-188 (ASVS Object Type)
Verify the application never reveals session tokens in URL parameters.
- Applicable: false
- ASVS ID: 3.1.1
- CWE: 598
- L1: Required
- L1 Text: ✓
- L2: Required
- L2 Text: ✓
- L3: Required
- L3 Text: ✓
- Ordinal: 1
- Type: Requirement

### ASVS-189: Session Binding (ASVS Object Type)
- ASVS ID: 3.2
- Ordinal: 2
- Type: Section

#### ASVS-190 (ASVS Object Type)
Verify the application generates a new session token on user authentication. (C6)
- Applicable: false
- ASVS ID: 3.2.1
- CWE: 384
- L1: Required
- L1 Text: ✓
- L2: Required
- L2 Text: ✓
- L3: Required
- L3 Text: ✓
- NIST §: 7.1
- Ordinal: 1
- Type: Requirement

#### ASVS-191 (ASVS Object Type)
Verify that session tokens possess at least 64 bits of entropy. (C6)
- Applicable: false
- ASVS ID: 3.2.2
- CWE: 331
- L1: Required
- L1 Text: ✓
- L2: Required
- L2 Text: ✓
- L3: Required
- L3 Text: ✓
- NIST §: 7.1
- Ordinal: 2
- Type: Requirement

#### ASVS-192 (ASVS Object Type)
Verify the application only stores session tokens in the browser using secure methods such as appropriately secured cookies (see section 3.4) or HTML 5 session storage.
- Applicable: false
- ASVS ID: 3.2.3
- CWE: 539
- L1: Required
- L1 Text: ✓
- L2: Required
- L2 Text: ✓
- L3: Required
- L3 Text: ✓
- NIST §: 7.1
- Ordinal: 3
- Type: Requirement

#### ASVS-193 (ASVS Object Type)
Verify that session tokens are generated using approved cryptographic algorithms. (C6)
- Applicable: false
- ASVS ID: 3.2.4
- CWE: 331
- L1: Not required
- L2: Required
- L2 Text: ✓
- L3: Required
- L3 Text: ✓
- NIST §: 7.1
- Ordinal: 4
- Type: Requirement

### ASVS-194: Session Termination (ASVS Object Type)
- ASVS ID: 3.3
- Ordinal: 3
- Type: Section

#### ASVS-195 (ASVS Object Type)
Verify that logout and expiration invalidate the session token, such that the back button or a downstream relying party does not resume an authenticated session, including across relying parties. (C6)
- Applicable: false
- ASVS ID: 3.3.1
- CWE: 613
- L1: Required
- L1 Text: ✓
- L2: Required
- L2 Text: ✓
- L3: Required
- L3 Text: ✓
- NIST §: 7.1
- Ordinal: 1
- Type: Requirement

#### ASVS-196 (ASVS Object Type)
If authenticators permit users to remain logged in, verify that re-authentication occurs periodically both when actively used or after an idle period. (C6)
- Applicable: false
- ASVS ID: 3.3.2
- CWE: 613
- L1: Required
- L1 Text: 30 days
- L2: Required
- L2 Text: 12 hours or 30 minutes of inactivity, 2FA optional
- L3: Required
- L3 Text: 12 hours or 15 minutes of inactivity, with 2FA
- NIST §: 7.2
- Ordinal: 2
- Type: Requirement

#### ASVS-197 (ASVS Object Type)
Verify that the application gives the option to terminate all other active sessions after a successful password change (including change via password reset/recovery), and that this is effective across the application, federated login (if present), and any relying parties.
- Applicable: false
- ASVS ID: 3.3.3
- CWE: 613
- L1: Not required
- L2: Required
- L2 Text: ✓
- L3: Required
- L3 Text: ✓
- Ordinal: 3
- Type: Requirement

#### ASVS-198 (ASVS Object Type)
Verify that users are able to view and (having re-entered login credentials) log out of any or all currently active sessions and devices.
- Applicable: false
- ASVS ID: 3.3.4
- CWE: 613
- L1: Not required
- L2: Required
- L2 Text: ✓
- L3: Required
- L3 Text: ✓
- NIST §: 7.1
- Ordinal: 4
- Type: Requirement

### ASVS-199: Cookie-based Session Management (ASVS Object Type)
- ASVS ID: 3.4
- Ordinal: 4
- Type: Section

#### ASVS-200 (ASVS Object Type)
Verify that cookie-based session tokens have the 'Secure' attribute set. (C6)
- Applicable: false
- ASVS ID: 3.4.1
- CWE: 614
- L1: Required
- L1 Text: ✓
- L2: Required
- L2 Text: ✓
- L3: Required
- L3 Text: ✓
- NIST §: 7.1.1
- Ordinal: 1
- Type: Requirement

#### ASVS-201 (ASVS Object Type)
Verify that cookie-based session tokens have the 'HttpOnly' attribute set. (C6)
- Applicable: false
- ASVS ID: 3.4.2
- CWE: 1004
- L1: Required
- L1 Text: ✓
- L2: Required
- L2 Text: ✓
- L3: Required
- L3 Text: ✓
- NIST §: 7.1.1
- Ordinal: 2
- Type: Requirement

#### ASVS-202 (ASVS Object Type)
Verify that cookie-based session tokens utilize the 'SameSite' attribute to limit exposure to cross-site request forgery attacks. (C6)
- Applicable: false
- ASVS ID: 3.4.3
- CWE: 1275
- L1: Required
- L1 Text: ✓
- L2: Required
- L2 Text: ✓
- L3: Required
- L3 Text: ✓
- NIST §: 7.1.1
- Ordinal: 3
- Type: Requirement

#### ASVS-203 (ASVS Object Type)
Verify that cookie-based session tokens use the "__Host-" prefix so cookies are only sent to the host that initially set the cookie.
- Applicable: false
- ASVS ID: 3.4.4
- CWE: 16
- L1: Required
- L1 Text: ✓
- L2: Required
- L2 Text: ✓
- L3: Required
- L3 Text: ✓
- NIST §: 7.1.1
- Ordinal: 4
- Type: Requirement

#### ASVS-204 (ASVS Object Type)
Verify that if the application is published under a domain name with other applications that set or use session cookies that might disclose the session cookies, set the path attribute in cookie-based session tokens using the most precise path possible. (C6)
- Applicable: false
- ASVS ID: 3.4.5
- CWE: 16
- L1: Required
- L1 Text: ✓
- L2: Required
- L2 Text: ✓
- L3: Required
- L3 Text: ✓
- NIST §: 7.1.1
- Ordinal: 5
- Type: Requirement

### ASVS-205: Token-based Session Management (ASVS Object Type)
- ASVS ID: 3.5
- Ordinal: 5
- Type: Section

#### ASVS-206 (ASVS Object Type)
Verify the application allows users to revoke OAuth tokens that form trust relationships with linked applications.
- Applicable: false
- ASVS ID: 3.5.1
- CWE: 290
- L1: Not required
- L2: Required
- L2 Text: ✓
- L3: Required
- L3 Text: ✓
- NIST §: 7.1.2
- Ordinal: 1
- Type: Requirement

#### ASVS-207 (ASVS Object Type)
Verify the application uses session tokens rather than static API secrets and keys, except with legacy implementations.
- Applicable: false
- ASVS ID: 3.5.2
- CWE: 798
- L1: Not required
- L2: Required
- L2 Text: ✓
- L3: Required
- L3 Text: ✓
- Ordinal: 2
- Type: Requirement

#### ASVS-208 (ASVS Object Type)
Verify that stateless session tokens use digital signatures, encryption, and other countermeasures to protect against tampering, enveloping, replay, null cipher, and key substitution attacks.
- Applicable: false
- ASVS ID: 3.5.3
- CWE: 345
- L1: Not required
- L2: Required
- L2 Text: ✓
- L3: Required
- L3 Text: ✓
- Ordinal: 3
- Type: Requirement

### ASVS-209: Federated Re-authentication (ASVS Object Type)
- ASVS ID: 3.6
- Ordinal: 6
- Type: Section

#### ASVS-210 (ASVS Object Type)
Verify that Relying Parties (RPs) specify the maximum authentication time to Credential Service Providers (CSPs) and that CSPs re-authenticate the user if they haven't used a session within that period.
- Applicable: false
- ASVS ID: 3.6.1
- CWE: 613
- L1: Not required
- L2: Not required
- L3: Required
- L3 Text: ✓
- NIST §: 7.2.1
- Ordinal: 1
- Type: Requirement

#### ASVS-211 (ASVS Object Type)
Verify that Credential Service Providers (CSPs) inform Relying Parties (RPs) of the last authentication event, to allow RPs to determine if they need to re-authenticate the user.
- Applicable: false
- ASVS ID: 3.6.2
- CWE: 613
- L1: Not required
- L2: Not required
- L3: Required
- L3 Text: ✓
- NIST §: 7.2.1
- Ordinal: 2
- Type: Requirement

### ASVS-212: Defenses Against Session Management Exploits (ASVS Object Type)
- ASVS ID: 3.7
- Ordinal: 7
- Type: Section

#### ASVS-213 (ASVS Object Type)
Verify the application ensures a full, valid login session or requires re-authentication or secondary verification before allowing any sensitive transactions or account modifications.
- Applicable: false
- ASVS ID: 3.7.1
- CWE: 306
- L1: Required
- L1 Text: ✓
- L2: Required
- L2 Text: ✓
- L3: Required
- L3 Text: ✓
- Ordinal: 1
- Type: Requirement

## ASVS-214: Access Control (ASVS Object Type)
- ASVS ID: 4
- Ordinal: 4
- Type: Section

### ASVS-215: General Access Control Design (ASVS Object Type)
- ASVS ID: 4.1
- Ordinal: 1
- Type: Section

#### ASVS-216 (ASVS Object Type)
Verify that the application enforces access control rules on a trusted service layer, especially if client-side access control is present and could be bypassed.
- Applicable: false
- ASVS ID: 4.1.1
- CWE: 602
- L1: Required
- L1 Text: ✓
- L2: Required
- L2 Text: ✓
- L3: Required
- L3 Text: ✓
- Ordinal: 1
- Type: Requirement

#### ASVS-217 (ASVS Object Type)
Verify that all user and data attributes and policy information used by access controls cannot be manipulated by end users unless specifically authorized.
- Applicable: false
- ASVS ID: 4.1.2
- CWE: 639
- L1: Required
- L1 Text: ✓
- L2: Required
- L2 Text: ✓
- L3: Required
- L3 Text: ✓
- Ordinal: 2
- Type: Requirement

#### ASVS-218 (ASVS Object Type)
Verify that the principle of least privilege exists - users should only be able to access functions, data files, URLs, controllers, services, and other resources, for which they possess specific authorization. This implies protection against spoofing and elevation of privilege. (C7)
- Applicable: false
- ASVS ID: 4.1.3
- CWE: 285
- L1: Required
- L1 Text: ✓
- L2: Required
- L2 Text: ✓
- L3: Required
- L3 Text: ✓
- Ordinal: 3
- Type: Requirement

#### ASVS-220 (ASVS Object Type)
Verify that access controls fail securely including when an exception occurs. (C10)
- Applicable: false
- ASVS ID: 4.1.5
- CWE: 285
- L1: Required
- L1 Text: ✓
- L2: Required
- L2 Text: ✓
- L3: Required
- L3 Text: ✓
- Ordinal: 5
- Type: Requirement

### ASVS-221: Operation Level Access Control (ASVS Object Type)
- ASVS ID: 4.2
- Ordinal: 2
- Type: Section

#### ASVS-222 (ASVS Object Type)
Verify that sensitive data and APIs are protected against Insecure Direct Object Reference (IDOR) attacks targeting creation, reading, updating and deletion of records, such as creating or updating someone else's record, viewing everyone's records, or deleting all records.
- Applicable: false
- ASVS ID: 4.2.1
- CWE: 639
- L1: Required
- L1 Text: ✓
- L2: Required
- L2 Text: ✓
- L3: Required
- L3 Text: ✓
- Ordinal: 1
- Type: Requirement

#### ASVS-223 (ASVS Object Type)
Verify that the application or framework enforces a strong anti-CSRF mechanism to protect authenticated functionality, and effective anti-automation or anti-CSRF protects unauthenticated functionality.
- Applicable: false
- ASVS ID: 4.2.2
- CWE: 352
- L1: Required
- L1 Text: ✓
- L2: Required
- L2 Text: ✓
- L3: Required
- L3 Text: ✓
- Ordinal: 2
- Type: Requirement

### ASVS-224: Other Access Control Considerations (ASVS Object Type)
- ASVS ID: 4.3
- Ordinal: 3
- Type: Section

#### ASVS-225 (ASVS Object Type)
Verify administrative interfaces use appropriate multi-factor authentication to prevent unauthorized use.
- Applicable: false
- ASVS ID: 4.3.1
- CWE: 419
- L1: Required
- L1 Text: ✓
- L2: Required
- L2 Text: ✓
- L3: Required
- L3 Text: ✓
- Ordinal: 1
- Type: Requirement

#### ASVS-226 (ASVS Object Type)
Verify that directory browsing is disabled unless deliberately desired. Additionally, applications should not allow discovery or disclosure of file or directory metadata, such as Thumbs.db, .DS_Store, .git or .svn folders.
- Applicable: false
- ASVS ID: 4.3.2
- CWE: 548
- L1: Required
- L1 Text: ✓
- L2: Required
- L2 Text: ✓
- L3: Required
- L3 Text: ✓
- Ordinal: 2
- Type: Requirement

#### ASVS-227 (ASVS Object Type)
Verify the application has additional authorization (such as step up or adaptive authentication) for lower value systems, and / or segregation of duties for high value applications to enforce anti-fraud controls as per the risk of application and past fraud.
- Applicable: false
- ASVS ID: 4.3.3
- CWE: 732
- L1: Not required
- L2: Required
- L2 Text: ✓
- L3: Required
- L3 Text: ✓
- Ordinal: 3
- Type: Requirement

## ASVS-228: Validation, Sanitization and Encoding (ASVS Object Type)
- ASVS ID: 5
- Ordinal: 5
- Type: Section

### ASVS-229: Input Validation (ASVS Object Type)
- ASVS ID: 5.1
- Ordinal: 1
- Type: Section

#### ASVS-230 (ASVS Object Type)
Verify that the application has defenses against HTTP parameter pollution attacks, particularly if the application framework makes no distinction about the source of request parameters (GET, POST, cookies, headers, or environment variables).
- Applicable: false
- ASVS ID: 5.1.1
- CWE: 235
- L1: Required
- L1 Text: ✓
- L2: Required
- L2 Text: ✓
- L3: Required
- L3 Text: ✓
- Ordinal: 1
- Type: Requirement

#### ASVS-231 (ASVS Object Type)
Verify that frameworks protect against mass parameter assignment attacks, or that the application has countermeasures to protect against unsafe parameter assignment, such as marking fields private or similar. (C5)
- Applicable: false
- ASVS ID: 5.1.2
- CWE: 915
- L1: Required
- L1 Text: ✓
- L2: Required
- L2 Text: ✓
- L3: Required
- L3 Text: ✓
- Ordinal: 2
- Type: Requirement

#### ASVS-232 (ASVS Object Type)
Verify that all input (HTML form fields, REST requests, URL parameters, HTTP headers, cookies, batch files, RSS feeds, etc) is validated using positive validation (allow lists). (C5)
- Applicable: true
- ASVS ID: 5.1.3
- CWE: 20
- L1: Required
- L1 Text: ✓
- L2: Required
- L2 Text: ✓
- L3: Required
- L3 Text: ✓
- Ordinal: 3
- Type: Requirement

#### ASVS-233 (ASVS Object Type)
Verify that structured data is strongly typed and validated against a defined schema including allowed characters, length and pattern (e.g. credit card numbers, e-mail addresses, telephone numbers, or validating that two related fields are reasonable, such as checking that suburb and zip/postcode match). (C5)
- Applicable: true
- ASVS ID: 5.1.4
- CWE: 20
- L1: Required
- L1 Text: ✓
- L2: Required
- L2 Text: ✓
- L3: Required
- L3 Text: ✓
- Ordinal: 4
- Type: Requirement

#### ASVS-234 (ASVS Object Type)
Verify that URL redirects and forwards only allow destinations which appear on an allow list, or show a warning when redirecting to potentially untrusted content.
- Applicable: true
- ASVS ID: 5.1.5
- CWE: 601
- L1: Required
- L1 Text: ✓
- L2: Required
- L2 Text: ✓
- L3: Required
- L3 Text: ✓
- Ordinal: 5
- Type: Requirement

### ASVS-235: Sanitization and Sandboxing (ASVS Object Type)
- ASVS ID: 5.2
- Ordinal: 2
- Type: Section

#### ASVS-236 (ASVS Object Type)
Verify that all untrusted HTML input from WYSIWYG editors or similar is properly sanitized with an HTML sanitizer library or framework feature. (C5)
- Applicable: true
- ASVS ID: 5.2.1
- CWE: 116
- L1: Required
- L1 Text: ✓
- L2: Required
- L2 Text: ✓
- L3: Required
- L3 Text: ✓
- Ordinal: 1
- Type: Requirement

#### ASVS-237 (ASVS Object Type)
Verify that unstructured data is sanitized to enforce safety measures such as allowed characters and length.
- Applicable: true
- ASVS ID: 5.2.2
- CWE: 138
- L1: Required
- L1 Text: ✓
- L2: Required
- L2 Text: ✓
- L3: Required
- L3 Text: ✓
- Ordinal: 2
- Type: Requirement

#### ASVS-238 (ASVS Object Type)
Verify that the application sanitizes user input before passing to mail systems to protect against SMTP or IMAP injection.
- Applicable: false
- ASVS ID: 5.2.3
- CWE: 147
- L1: Required
- L1 Text: ✓
- L2: Required
- L2 Text: ✓
- L3: Required
- L3 Text: ✓
- Ordinal: 3
- Type: Requirement

#### ASVS-239 (ASVS Object Type)
Verify that the application avoids the use of eval() or other dynamic code execution features. Where there is no alternative, any user input being included must be sanitized or sandboxed before being executed.
- Applicable: true
- ASVS ID: 5.2.4
- CWE: 95
- L1: Required
- L1 Text: ✓
- L2: Required
- L2 Text: ✓
- L3: Required
- L3 Text: ✓
- Ordinal: 4
- Type: Requirement

#### ASVS-240 (ASVS Object Type)
Verify that the application protects against template injection attacks by ensuring that any user input being included is sanitized or sandboxed.
- Applicable: true
- ASVS ID: 5.2.5
- CWE: 94
- L1: Required
- L1 Text: ✓
- L2: Required
- L2 Text: ✓
- L3: Required
- L3 Text: ✓
- Ordinal: 5
- Type: Requirement

#### ASVS-241 (ASVS Object Type)
Verify that the application protects against SSRF attacks, by validating or sanitizing untrusted data or HTTP file metadata, such as filenames and URL input fields, and uses allow lists of protocols, domains, paths and ports.
- Applicable: false
- ASVS ID: 5.2.6
- CWE: 918
- L1: Required
- L1 Text: ✓
- L2: Required
- L2 Text: ✓
- L3: Required
- L3 Text: ✓
- Ordinal: 6
- Type: Requirement

#### ASVS-242 (ASVS Object Type)
Verify that the application sanitizes, disables, or sandboxes user-supplied Scalable Vector Graphics (SVG) scriptable content, especially as they relate to XSS resulting from inline scripts, and foreignObject.
- Applicable: true
- ASVS ID: 5.2.7
- CWE: 159
- L1: Required
- L1 Text: ✓
- L2: Required
- L2 Text: ✓
- L3: Required
- L3 Text: ✓
- Ordinal: 7
- Type: Requirement

#### ASVS-243 (ASVS Object Type)
Verify that the application sanitizes, disables, or sandboxes user-supplied scriptable or expression template language content, such as Markdown, CSS or XSL stylesheets, BBCode, or similar.
- Applicable: false
- ASVS ID: 5.2.8
- CWE: 94
- L1: Required
- L1 Text: ✓
- L2: Required
- L2 Text: ✓
- L3: Required
- L3 Text: ✓
- Ordinal: 8
- Type: Requirement

### ASVS-244: Output Encoding and Injection Prevention (ASVS Object Type)
- ASVS ID: 5.3
- Ordinal: 3
- Type: Section

#### ASVS-245 (ASVS Object Type)
Verify that output encoding is relevant for the interpreter and context required. For example, use encoders specifically for HTML values, HTML attributes, JavaScript, URL parameters, HTTP headers, SMTP, and others as the context requires, especially from untrusted inputs (e.g. names with Unicode or apostrophes, such as ねこ or O'Hara). (C4)
- Applicable: true
- ASVS ID: 5.3.1
- CWE: 116
- L1: Required
- L1 Text: ✓
- L2: Required
- L2 Text: ✓
- L3: Required
- L3 Text: ✓
- Ordinal: 1
- Type: Requirement

#### ASVS-246 (ASVS Object Type)
Verify that output encoding preserves the user's chosen character set and locale, such that any Unicode character point is valid and safely handled. (C4)
- Applicable: true
- ASVS ID: 5.3.2
- CWE: 176
- L1: Required
- L1 Text: ✓
- L2: Required
- L2 Text: ✓
- L3: Required
- L3 Text: ✓
- Ordinal: 2
- Type: Requirement

#### ASVS-247 (ASVS Object Type)
Verify that context-aware, preferably automated - or at worst, manual - output escaping protects against reflected, stored, and DOM based XSS. (C4)
- Applicable: true
- ASVS ID: 5.3.3
- CWE: 79
- L1: Required
- L1 Text: ✓
- L2: Required
- L2 Text: ✓
- L3: Required
- L3 Text: ✓
- Ordinal: 3
- Type: Requirement

#### ASVS-248 (ASVS Object Type)
Verify that data selection or database queries (e.g. SQL, HQL, ORM, NoSQL) use parameterized queries, ORMs, entity frameworks, or are otherwise protected from database injection attacks. (C3)
- Applicable: false
- ASVS ID: 5.3.4
- CWE: 89
- L1: Required
- L1 Text: ✓
- L2: Required
- L2 Text: ✓
- L3: Required
- L3 Text: ✓
- Ordinal: 4
- Type: Requirement

#### ASVS-249 (ASVS Object Type)
Verify that where parameterized or safer mechanisms are not present, context-specific output encoding is used to protect against injection attacks, such as the use of SQL escaping to protect against SQL injection. (C3, C4)
- Applicable: false
- ASVS ID: 5.3.5
- CWE: 89
- L1: Required
- L1 Text: ✓
- L2: Required
- L2 Text: ✓
- L3: Required
- L3 Text: ✓
- Ordinal: 5
- Type: Requirement

#### ASVS-250 (ASVS Object Type)
Verify that the application protects against JSON injection attacks, JSON eval attacks, and JavaScript expression evaluation. (C4)
- Applicable: true
- ASVS ID: 5.3.6
- CWE: 830
- L1: Required
- L1 Text: ✓
- L2: Required
- L2 Text: ✓
- L3: Required
- L3 Text: ✓
- Ordinal: 6
- Type: Requirement

#### ASVS-251 (ASVS Object Type)
Verify that the application protects against LDAP injection vulnerabilities, or that specific security controls to prevent LDAP injection have been implemented. (C4)
- Applicable: false
- ASVS ID: 5.3.7
- CWE: 90
- L1: Required
- L1 Text: ✓
- L2: Required
- L2 Text: ✓
- L3: Required
- L3 Text: ✓
- Ordinal: 7
- Type: Requirement

#### ASVS-252 (ASVS Object Type)
Verify that the application protects against OS command injection and that operating system calls use parameterized OS queries or use contextual command line output encoding. (C4)
- Applicable: false
- ASVS ID: 5.3.8
- CWE: 78
- L1: Required
- L1 Text: ✓
- L2: Required
- L2 Text: ✓
- L3: Required
- L3 Text: ✓
- Ordinal: 8
- Type: Requirement

#### ASVS-253 (ASVS Object Type)
Verify that the application protects against Local File Inclusion (LFI) or Remote File Inclusion (RFI) attacks.
- Applicable: false
- ASVS ID: 5.3.9
- CWE: 829
- L1: Required
- L1 Text: ✓
- L2: Required
- L2 Text: ✓
- L3: Required
- L3 Text: ✓
- Ordinal: 9
- Type: Requirement

#### ASVS-254 (ASVS Object Type)
Verify that the application protects against XPath injection or XML injection attacks. (C4)
- Applicable: false
- ASVS ID: 5.3.10
- CWE: 643
- L1: Required
- L1 Text: ✓
- L2: Required
- L2 Text: ✓
- L3: Required
- L3 Text: ✓
- Ordinal: 10
- Type: Requirement

### ASVS-255: Memory, String, and Unmanaged Code (ASVS Object Type)
- ASVS ID: 5.4
- Ordinal: 4
- Type: Section

#### ASVS-256 (ASVS Object Type)
Verify that the application uses memory-safe string, safer memory copy and pointer arithmetic to detect or prevent stack, buffer, or heap overflows.
- Applicable: false
- ASVS ID: 5.4.1
- CWE: 120
- L1: Not required
- L2: Required
- L2 Text: ✓
- L3: Required
- L3 Text: ✓
- Ordinal: 1
- Type: Requirement

#### ASVS-257 (ASVS Object Type)
Verify that format strings do not take potentially hostile input, and are constant.
- Applicable: false
- ASVS ID: 5.4.2
- CWE: 134
- L1: Not required
- L2: Required
- L2 Text: ✓
- L3: Required
- L3 Text: ✓
- Ordinal: 2
- Type: Requirement

#### ASVS-258 (ASVS Object Type)
Verify that sign, range, and input validation techniques are used to prevent integer overflows.
- Applicable: false
- ASVS ID: 5.4.3
- CWE: 190
- L1: Not required
- L2: Required
- L2 Text: ✓
- L3: Required
- L3 Text: ✓
- Ordinal: 3
- Type: Requirement

### ASVS-259: Deserialization Prevention (ASVS Object Type)
- ASVS ID: 5.5
- Ordinal: 5
- Type: Section

#### ASVS-260 (ASVS Object Type)
Verify that serialized objects use integrity checks or are encrypted to prevent hostile object creation or data tampering. (C5)
- Applicable: false
- ASVS ID: 5.5.1
- CWE: 502
- L1: Required
- L1 Text: ✓
- L2: Required
- L2 Text: ✓
- L3: Required
- L3 Text: ✓
- Ordinal: 1
- Type: Requirement

#### ASVS-261 (ASVS Object Type)
Verify that the application correctly restricts XML parsers to only use the most restrictive configuration possible and to ensure that unsafe features such as resolving external entities are disabled to prevent XML eXternal Entity (XXE) attacks.
- Applicable: false
- ASVS ID: 5.5.2
- CWE: 611
- L1: Required
- L1 Text: ✓
- L2: Required
- L2 Text: ✓
- L3: Required
- L3 Text: ✓
- Ordinal: 2
- Type: Requirement

#### ASVS-262 (ASVS Object Type)
Verify that deserialization of untrusted data is avoided or is protected in both custom code and third-party libraries (such as JSON, XML and YAML parsers).
- Applicable: false
- ASVS ID: 5.5.3
- CWE: 502
- L1: Required
- L1 Text: ✓
- L2: Required
- L2 Text: ✓
- L3: Required
- L3 Text: ✓
- Ordinal: 3
- Type: Requirement

#### ASVS-263 (ASVS Object Type)
Verify that when parsing JSON in browsers or JavaScript-based backends, JSON.parse is used to parse the JSON document. Do not use eval() to parse JSON.
- Applicable: true
- ASVS ID: 5.5.4
- CWE: 95
- L1: Required
- L1 Text: ✓
- L2: Required
- L2 Text: ✓
- L3: Required
- L3 Text: ✓
- Ordinal: 4
- Type: Requirement

## ASVS-264: Stored Cryptography (ASVS Object Type)
- ASVS ID: 6
- Ordinal: 6
- Type: Section

### ASVS-265: Data Classification (ASVS Object Type)
- ASVS ID: 6.1
- Ordinal: 1
- Type: Section

#### ASVS-266 (ASVS Object Type)
Verify that regulated private data is stored encrypted while at rest, such as Personally Identifiable Information (PII), sensitive personal information, or data assessed likely to be subject to EU's GDPR.
- Applicable: false
- ASVS ID: 6.1.1
- CWE: 311
- L1: Not required
- L2: Required
- L2 Text: ✓
- L3: Required
- L3 Text: ✓
- Ordinal: 1
- Type: Requirement

#### ASVS-267 (ASVS Object Type)
Verify that regulated health data is stored encrypted while at rest, such as medical records, medical device details, or de-anonymized research records.
- Applicable: false
- ASVS ID: 6.1.2
- CWE: 311
- L1: Not required
- L2: Required
- L2 Text: ✓
- L3: Required
- L3 Text: ✓
- Ordinal: 2
- Type: Requirement

#### ASVS-268 (ASVS Object Type)
Verify that regulated financial data is stored encrypted while at rest, such as financial accounts, defaults or credit history, tax records, pay history, beneficiaries, or de-anonymized market or research records.
- Applicable: false
- ASVS ID: 6.1.3
- CWE: 311
- L1: Not required
- L2: Required
- L2 Text: ✓
- L3: Required
- L3 Text: ✓
- Ordinal: 3
- Type: Requirement

### ASVS-269: Algorithms (ASVS Object Type)
- ASVS ID: 6.2
- Ordinal: 2
- Type: Section

#### ASVS-270 (ASVS Object Type)
Verify that all cryptographic modules fail securely, and errors are handled in a way that does not enable Padding Oracle attacks.
- Applicable: false
- ASVS ID: 6.2.1
- CWE: 310
- L1: Required
- L1 Text: ✓
- L2: Required
- L2 Text: ✓
- L3: Required
- L3 Text: ✓
- Ordinal: 1
- Type: Requirement

#### ASVS-271 (ASVS Object Type)
Verify that industry proven or government approved cryptographic algorithms, modes, and libraries are used, instead of custom coded cryptography. (C8)
- Applicable: false
- ASVS ID: 6.2.2
- CWE: 327
- L1: Not required
- L2: Required
- L2 Text: ✓
- L3: Required
- L3 Text: ✓
- Ordinal: 2
- Type: Requirement

#### ASVS-272 (ASVS Object Type)
Verify that encryption initialization vector, cipher configuration, and block modes are configured securely using the latest advice.
- Applicable: false
- ASVS ID: 6.2.3
- CWE: 326
- L1: Not required
- L2: Required
- L2 Text: ✓
- L3: Required
- L3 Text: ✓
- Ordinal: 3
- Type: Requirement

#### ASVS-273 (ASVS Object Type)
Verify that random number, encryption or hashing algorithms, key lengths, rounds, ciphers or modes, can be reconfigured, upgraded, or swapped at any time, to protect against cryptographic breaks. (C8)
- Applicable: false
- ASVS ID: 6.2.4
- CWE: 326
- L1: Not required
- L2: Required
- L2 Text: ✓
- L3: Required
- L3 Text: ✓
- Ordinal: 4
- Type: Requirement

#### ASVS-274 (ASVS Object Type)
Verify that known insecure block modes (i.e. ECB, etc.), padding modes (i.e. PKCS#1 v1.5, etc.), ciphers with small block sizes (i.e. Triple-DES, Blowfish, etc.), and weak hashing algorithms (i.e. MD5, SHA1, etc.) are not used unless required for backwards compatibility.
- Applicable: false
- ASVS ID: 6.2.5
- CWE: 326
- L1: Not required
- L2: Required
- L2 Text: ✓
- L3: Required
- L3 Text: ✓
- Ordinal: 5
- Type: Requirement

#### ASVS-275 (ASVS Object Type)
Verify that nonces, initialization vectors, and other single use numbers must not be used more than once with a given encryption key. The method of generation must be appropriate for the algorithm being used.
- Applicable: false
- ASVS ID: 6.2.6
- CWE: 326
- L1: Not required
- L2: Required
- L2 Text: ✓
- L3: Required
- L3 Text: ✓
- Ordinal: 6
- Type: Requirement

#### ASVS-276 (ASVS Object Type)
Verify that encrypted data is authenticated via signatures, authenticated cipher modes, or HMAC to ensure that ciphertext is not altered by an unauthorized party.
- Applicable: false
- ASVS ID: 6.2.7
- CWE: 326
- L1: Not required
- L2: Not required
- L3: Required
- L3 Text: ✓
- Ordinal: 7
- Type: Requirement

#### ASVS-277 (ASVS Object Type)
Verify that all cryptographic operations are constant-time, with no 'short-circuit' operations in comparisons, calculations, or returns, to avoid leaking information.
- Applicable: false
- ASVS ID: 6.2.8
- CWE: 385
- L1: Not required
- L2: Not required
- L3: Required
- L3 Text: ✓
- Ordinal: 8
- Type: Requirement

### ASVS-278: Random Values (ASVS Object Type)
- ASVS ID: 6.3
- Ordinal: 3
- Type: Section

#### ASVS-279 (ASVS Object Type)
Verify that all random numbers, random file names, random GUIDs, and random strings are generated using the cryptographic module's approved cryptographically secure random number generator when these random values are intended to be not guessable by an attacker.
- Applicable: false
- ASVS ID: 6.3.1
- CWE: 338
- L1: Not required
- L2: Required
- L2 Text: ✓
- L3: Required
- L3 Text: ✓
- Ordinal: 1
- Type: Requirement

#### ASVS-280 (ASVS Object Type)
Verify that random GUIDs are created using the GUID v4 algorithm, and a Cryptographically-secure Pseudo-random Number Generator (CSPRNG). GUIDs created using other pseudo-random number generators may be predictable.
- Applicable: false
- ASVS ID: 6.3.2
- CWE: 338
- L1: Not required
- L2: Required
- L2 Text: ✓
- L3: Required
- L3 Text: ✓
- Ordinal: 2
- Type: Requirement

#### ASVS-281 (ASVS Object Type)
Verify that random numbers are created with proper entropy even when the application is under heavy load, or that the application degrades gracefully in such circumstances.
- Applicable: false
- ASVS ID: 6.3.3
- CWE: 338
- L1: Not required
- L2: Not required
- L3: Required
- L3 Text: ✓
- Ordinal: 3
- Type: Requirement

### ASVS-282: Secret Management (ASVS Object Type)
- ASVS ID: 6.4
- Ordinal: 4
- Type: Section

#### ASVS-283 (ASVS Object Type)
Verify that a secrets management solution such as a key vault is used to securely create, store, control access to and destroy secrets. (C8)
- Applicable: false
- ASVS ID: 6.4.1
- CWE: 798
- L1: Not required
- L2: Required
- L2 Text: ✓
- L3: Required
- L3 Text: ✓
- Ordinal: 1
- Type: Requirement

#### ASVS-284 (ASVS Object Type)
Verify that key material is not exposed to the application but instead uses an isolated security module like a vault for cryptographic operations. (C8)
- Applicable: false
- ASVS ID: 6.4.2
- CWE: 320
- L1: Not required
- L2: Required
- L2 Text: ✓
- L3: Required
- L3 Text: ✓
- Ordinal: 2
- Type: Requirement

## ASVS-285: Error Handling and Logging (ASVS Object Type)
- ASVS ID: 7
- Ordinal: 7
- Type: Section

### ASVS-286: Log Content (ASVS Object Type)
- ASVS ID: 7.1
- Ordinal: 1
- Type: Section

#### ASVS-287 (ASVS Object Type)
Verify that the application does not log credentials or payment details. Session tokens should only be stored in logs in an irreversible, hashed form. (C9, C10)
- Applicable: true
- ASVS ID: 7.1.1
- CWE: 532
- L1: Required
- L1 Text: ✓
- L2: Required
- L2 Text: ✓
- L3: Required
- L3 Text: ✓
- Ordinal: 1
- Type: Requirement

#### ASVS-288 (ASVS Object Type)
Verify that the application does not log other sensitive data as defined under local privacy laws or relevant security policy. (C9)
- Applicable: true
- ASVS ID: 7.1.2
- CWE: 532
- L1: Required
- L1 Text: ✓
- L2: Required
- L2 Text: ✓
- L3: Required
- L3 Text: ✓
- Ordinal: 2
- Type: Requirement

#### ASVS-289 (ASVS Object Type)
Verify that the application logs security relevant events including successful and failed authentication events, access control failures, deserialization failures and input validation failures. (C5, C7)
- Applicable: false
- ASVS ID: 7.1.3
- CWE: 778
- L1: Not required
- L2: Required
- L2 Text: ✓
- L3: Required
- L3 Text: ✓
- Ordinal: 3
- Type: Requirement

#### ASVS-290 (ASVS Object Type)
Verify that each log event includes necessary information that would allow for a detailed investigation of the timeline when an event happens. (C9)
- Applicable: false
- ASVS ID: 7.1.4
- CWE: 778
- L1: Not required
- L2: Required
- L2 Text: ✓
- L3: Required
- L3 Text: ✓
- Ordinal: 4
- Type: Requirement

### ASVS-291: Log Processing (ASVS Object Type)
- ASVS ID: 7.2
- Ordinal: 2
- Type: Section

#### ASVS-292 (ASVS Object Type)
Verify that all authentication decisions are logged, without storing sensitive session tokens or passwords. This should include requests with relevant metadata needed for security investigations.
- Applicable: false
- ASVS ID: 7.2.1
- CWE: 778
- L1: Not required
- L2: Required
- L2 Text: ✓
- L3: Required
- L3 Text: ✓
- Ordinal: 1
- Type: Requirement

#### ASVS-293 (ASVS Object Type)
Verify that all access control decisions can be logged and all failed decisions are logged. This should include requests with relevant metadata needed for security investigations.
- Applicable: false
- ASVS ID: 7.2.2
- CWE: 285
- L1: Not required
- L2: Required
- L2 Text: ✓
- L3: Required
- L3 Text: ✓
- Ordinal: 2
- Type: Requirement

### ASVS-294: Log Protection (ASVS Object Type)
- ASVS ID: 7.3
- Ordinal: 3
- Type: Section

#### ASVS-295 (ASVS Object Type)
Verify that all logging components appropriately encode data to prevent log injection. (C9)
- Applicable: false
- ASVS ID: 7.3.1
- CWE: 117
- L1: Not required
- L2: Required
- L2 Text: ✓
- L3: Required
- L3 Text: ✓
- Ordinal: 1
- Type: Requirement

#### ASVS-297 (ASVS Object Type)
Verify that security logs are protected from unauthorized access and modification. (C9)
- Applicable: false
- ASVS ID: 7.3.3
- CWE: 200
- L1: Not required
- L2: Required
- L2 Text: ✓
- L3: Required
- L3 Text: ✓
- Ordinal: 3
- Type: Requirement

#### ASVS-298 (ASVS Object Type)
Verify that time sources are synchronized to the correct time and time zone. Strongly consider logging only in UTC if systems are global to assist with post-incident forensic analysis. (C9)
- Applicable: false
- ASVS ID: 7.3.4
- L1: Not required
- L2: Required
- L2 Text: ✓
- L3: Required
- L3 Text: ✓
- Ordinal: 4
- Type: Requirement

### ASVS-299: Error Handling (ASVS Object Type)
- ASVS ID: 7.4
- Ordinal: 4
- Type: Section

#### ASVS-300 (ASVS Object Type)
Verify that a generic message is shown when an unexpected or security sensitive error occurs, potentially with a unique ID which support personnel can use to investigate. (C10)
- Applicable: false
- ASVS ID: 7.4.1
- CWE: 210
- L1: Required
- L1 Text: ✓
- L2: Required
- L2 Text: ✓
- L3: Required
- L3 Text: ✓
- Ordinal: 1
- Type: Requirement

#### ASVS-301 (ASVS Object Type)
Verify that exception handling (or a functional equivalent) is used across the codebase to account for expected and unexpected error conditions. (C10)
- Applicable: false
- ASVS ID: 7.4.2
- CWE: 544
- L1: Not required
- L2: Required
- L2 Text: ✓
- L3: Required
- L3 Text: ✓
- Ordinal: 2
- Type: Requirement

#### ASVS-302 (ASVS Object Type)
Verify that a "last resort" error handler is defined which will catch all unhandled exceptions. (C10)
- Applicable: false
- ASVS ID: 7.4.3
- CWE: 431
- L1: Not required
- L2: Required
- L2 Text: ✓
- L3: Required
- L3 Text: ✓
- Ordinal: 3
- Type: Requirement

## ASVS-303: Data Protection (ASVS Object Type)
- ASVS ID: 8
- Ordinal: 8
- Type: Section

### ASVS-304: General Data Protection (ASVS Object Type)
- ASVS ID: 8.1
- Ordinal: 1
- Type: Section

#### ASVS-305 (ASVS Object Type)
Verify the application protects sensitive data from being cached in server components such as load balancers and application caches.
- Applicable: false
- ASVS ID: 8.1.1
- CWE: 524
- L1: Not required
- L2: Required
- L2 Text: ✓
- L3: Required
- L3 Text: ✓
- Ordinal: 1
- Type: Requirement

#### ASVS-306 (ASVS Object Type)
Verify that all cached or temporary copies of sensitive data stored on the server are protected from unauthorized access or purged/invalidated after the authorized user accesses the sensitive data.
- Applicable: false
- ASVS ID: 8.1.2
- CWE: 524
- L1: Not required
- L2: Required
- L2 Text: ✓
- L3: Required
- L3 Text: ✓
- Ordinal: 2
- Type: Requirement

#### ASVS-307 (ASVS Object Type)
Verify the application minimizes the number of parameters in a request, such as hidden fields, Ajax variables, cookies and header values.
- Applicable: false
- ASVS ID: 8.1.3
- CWE: 233
- L1: Not required
- L2: Required
- L2 Text: ✓
- L3: Required
- L3 Text: ✓
- Ordinal: 3
- Type: Requirement

#### ASVS-308 (ASVS Object Type)
Verify the application can detect and alert on abnormal numbers of requests, such as by IP, user, total per hour or day, or whatever makes sense for the application.
- Applicable: false
- ASVS ID: 8.1.4
- CWE: 770
- L1: Not required
- L2: Required
- L2 Text: ✓
- L3: Required
- L3 Text: ✓
- Ordinal: 4
- Type: Requirement

#### ASVS-309 (ASVS Object Type)
Verify that regular backups of important data are performed and that test restoration of data is performed.
- Applicable: false
- ASVS ID: 8.1.5
- CWE: 19
- L1: Not required
- L2: Not required
- L3: Required
- L3 Text: ✓
- Ordinal: 5
- Type: Requirement

#### ASVS-310 (ASVS Object Type)
Verify that backups are stored securely to prevent data from being stolen or corrupted.
- Applicable: false
- ASVS ID: 8.1.6
- CWE: 19
- L1: Not required
- L2: Not required
- L3: Required
- L3 Text: ✓
- Ordinal: 6
- Type: Requirement

### ASVS-311: Client-side Data Protection (ASVS Object Type)
- ASVS ID: 8.2
- Ordinal: 2
- Type: Section

#### ASVS-312 (ASVS Object Type)
Verify the application sets sufficient anti-caching headers so that sensitive data is not cached in modern browsers.
- Applicable: false
- ASVS ID: 8.2.1
- CWE: 525
- L1: Required
- L1 Text: ✓
- L2: Required
- L2 Text: ✓
- L3: Required
- L3 Text: ✓
- Ordinal: 1
- Type: Requirement

#### ASVS-313 (ASVS Object Type)
Verify that data stored in browser storage (such as localStorage, sessionStorage, IndexedDB, or cookies) does not contain sensitive data.
- Applicable: false
- ASVS ID: 8.2.2
- CWE: 922
- L1: Required
- L1 Text: ✓
- L2: Required
- L2 Text: ✓
- L3: Required
- L3 Text: ✓
- Ordinal: 2
- Type: Requirement

#### ASVS-314 (ASVS Object Type)
Verify that authenticated data is cleared from client storage, such as the browser DOM, after the client or session is terminated.
- Applicable: false
- ASVS ID: 8.2.3
- CWE: 922
- L1: Required
- L1 Text: ✓
- L2: Required
- L2 Text: ✓
- L3: Required
- L3 Text: ✓
- Ordinal: 3
- Type: Requirement

### ASVS-315: Sensitive Private Data (ASVS Object Type)
- ASVS ID: 8.3
- Ordinal: 3
- Type: Section

#### ASVS-316 (ASVS Object Type)
Verify that sensitive data is sent to the server in the HTTP message body or headers, and that query string parameters from any HTTP verb do not contain sensitive data.
- Applicable: false
- ASVS ID: 8.3.1
- CWE: 319
- L1: Required
- L1 Text: ✓
- L2: Required
- L2 Text: ✓
- L3: Required
- L3 Text: ✓
- Ordinal: 1
- Type: Requirement

#### ASVS-317 (ASVS Object Type)
Verify that users have a method to remove or export their data on demand.
- Applicable: false
- ASVS ID: 8.3.2
- CWE: 212
- L1: Required
- L1 Text: ✓
- L2: Required
- L2 Text: ✓
- L3: Required
- L3 Text: ✓
- Ordinal: 2
- Type: Requirement

#### ASVS-318 (ASVS Object Type)
Verify that users are provided clear language regarding collection and use of supplied personal information and that users have provided opt-in consent for the use of that data before it is used in any way.
- Applicable: true
- ASVS ID: 8.3.3
- CWE: 285
- L1: Required
- L1 Text: ✓
- L2: Required
- L2 Text: ✓
- L3: Required
- L3 Text: ✓
- Ordinal: 3
- Type: Requirement

#### ASVS-319 (ASVS Object Type)
Verify that all sensitive data created and processed by the application has been identified, and ensure that a policy is in place on how to deal with sensitive data. (C8)
- Applicable: true
- ASVS ID: 8.3.4
- CWE: 200
- L1: Required
- L1 Text: ✓
- L2: Required
- L2 Text: ✓
- L3: Required
- L3 Text: ✓
- Ordinal: 4
- Type: Requirement

#### ASVS-320 (ASVS Object Type)
Verify accessing sensitive data is audited (without logging the sensitive data itself), if the data is collected under relevant data protection directives or where logging of access is required.
- Applicable: false
- ASVS ID: 8.3.5
- CWE: 532
- L1: Not required
- L2: Required
- L2 Text: ✓
- L3: Required
- L3 Text: ✓
- Ordinal: 5
- Type: Requirement

#### ASVS-321 (ASVS Object Type)
Verify that sensitive information contained in memory is overwritten as soon as it is no longer required to mitigate memory dumping attacks, using zeroes or random data.
- Applicable: false
- ASVS ID: 8.3.6
- CWE: 226
- L1: Not required
- L2: Required
- L2 Text: ✓
- L3: Required
- L3 Text: ✓
- Ordinal: 6
- Type: Requirement

#### ASVS-322 (ASVS Object Type)
Verify that sensitive or private information that is required to be encrypted, is encrypted using approved algorithms that provide both confidentiality and integrity. (C8)
- Applicable: false
- ASVS ID: 8.3.7
- CWE: 327
- L1: Not required
- L2: Required
- L2 Text: ✓
- L3: Required
- L3 Text: ✓
- Ordinal: 7
- Type: Requirement

#### ASVS-323 (ASVS Object Type)
Verify that sensitive personal information is subject to data retention classification, such that old or out of date data is deleted automatically, on a schedule, or as the situation requires.
- Applicable: false
- ASVS ID: 8.3.8
- CWE: 285
- L1: Not required
- L2: Required
- L2 Text: ✓
- L3: Required
- L3 Text: ✓
- Ordinal: 8
- Type: Requirement

## ASVS-324: Communication (ASVS Object Type)
- ASVS ID: 9
- Ordinal: 9
- Type: Section

### ASVS-325: Client Communication Security (ASVS Object Type)
- ASVS ID: 9.1
- Ordinal: 1
- Type: Section

#### ASVS-326 (ASVS Object Type)
Verify that TLS is used for all client connectivity, and does not fall back to insecure or unencrypted communications. (C8)
- Applicable: false
- ASVS ID: 9.1.1
- CWE: 319
- L1: Required
- L1 Text: ✓
- L2: Required
- L2 Text: ✓
- L3: Required
- L3 Text: ✓
- Ordinal: 1
- Type: Requirement

#### ASVS-327 (ASVS Object Type)
Verify using up to date TLS testing tools that only strong cipher suites are enabled, with the strongest cipher suites set as preferred.
- Applicable: false
- ASVS ID: 9.1.2
- CWE: 326
- L1: Required
- L1 Text: ✓
- L2: Required
- L2 Text: ✓
- L3: Required
- L3 Text: ✓
- Ordinal: 2
- Type: Requirement

#### ASVS-328 (ASVS Object Type)
Verify that only the latest recommended versions of the TLS protocol are enabled, such as TLS 1.2 and TLS 1.3. The latest version of the TLS protocol should be the preferred option.
- Applicable: false
- ASVS ID: 9.1.3
- CWE: 326
- L1: Required
- L1 Text: ✓
- L2: Required
- L2 Text: ✓
- L3: Required
- L3 Text: ✓
- Ordinal: 3
- Type: Requirement

### ASVS-329: Server Communication Security (ASVS Object Type)
- ASVS ID: 9.2
- Ordinal: 2
- Type: Section

#### ASVS-330 (ASVS Object Type)
Verify that connections to and from the server use trusted TLS certificates. Where internally generated or self-signed certificates are used, the server must be configured to only trust specific internal CAs and specific self-signed certificates. All others should be rejected.
- Applicable: false
- ASVS ID: 9.2.1
- CWE: 295
- L1: Not required
- L2: Required
- L2 Text: ✓
- L3: Required
- L3 Text: ✓
- Ordinal: 1
- Type: Requirement

#### ASVS-331 (ASVS Object Type)
Verify that encrypted communications such as TLS is used for all inbound and outbound connections, including for management ports, monitoring, authentication, API, or web service calls, database, cloud, serverless, mainframe, external, and partner connections. The server must not fall back to insecure or unencrypted protocols.
- Applicable: false
- ASVS ID: 9.2.2
- CWE: 319
- L1: Not required
- L2: Required
- L2 Text: ✓
- L3: Required
- L3 Text: ✓
- Ordinal: 2
- Type: Requirement

#### ASVS-332 (ASVS Object Type)
Verify that all encrypted connections to external systems that involve sensitive information or functions are authenticated.
- Applicable: false
- ASVS ID: 9.2.3
- CWE: 287
- L1: Not required
- L2: Required
- L2 Text: ✓
- L3: Required
- L3 Text: ✓
- Ordinal: 3
- Type: Requirement

#### ASVS-333 (ASVS Object Type)
Verify that proper certification revocation, such as Online Certificate Status Protocol (OCSP) Stapling, is enabled and configured.
- Applicable: false
- ASVS ID: 9.2.4
- CWE: 299
- L1: Not required
- L2: Required
- L2 Text: ✓
- L3: Required
- L3 Text: ✓
- Ordinal: 4
- Type: Requirement

#### ASVS-334 (ASVS Object Type)
Verify that backend TLS connection failures are logged.
- Applicable: false
- ASVS ID: 9.2.5
- CWE: 544
- L1: Not required
- L2: Not required
- L3: Required
- L3 Text: ✓
- Ordinal: 5
- Type: Requirement

## ASVS-335: Malicious Code (ASVS Object Type)
- ASVS ID: 10
- Ordinal: 10
- Type: Section

### ASVS-336: Code Integrity (ASVS Object Type)
- ASVS ID: 10.1
- Ordinal: 1
- Type: Section

#### ASVS-337 (ASVS Object Type)
Verify that a code analysis tool is in use that can detect potentially malicious code, such as time functions, unsafe file operations and network connections.
- Applicable: false
- ASVS ID: 10.1.1
- CWE: 749
- L1: Not required
- L2: Not required
- L3: Required
- L3 Text: ✓
- Ordinal: 1
- Type: Requirement

### ASVS-338: Malicious Code Search (ASVS Object Type)
- ASVS ID: 10.2
- Ordinal: 2
- Type: Section

#### ASVS-339 (ASVS Object Type)
Verify that the application source code and third party libraries do not contain unauthorized phone home or data collection capabilities. Where such functionality exists, obtain the user's permission for it to operate before collecting any data.
- Applicable: false
- ASVS ID: 10.2.1
- CWE: 359
- L1: Not required
- L2: Required
- L2 Text: ✓
- L3: Required
- L3 Text: ✓
- Ordinal: 1
- Type: Requirement

#### ASVS-340 (ASVS Object Type)
Verify that the application does not ask for unnecessary or excessive permissions to privacy related features or sensors, such as contacts, cameras, microphones, or location.
- Applicable: false
- ASVS ID: 10.2.2
- CWE: 272
- L1: Not required
- L2: Required
- L2 Text: ✓
- L3: Required
- L3 Text: ✓
- Ordinal: 2
- Type: Requirement

#### ASVS-341 (ASVS Object Type)
Verify that the application source code and third party libraries do not contain back doors, such as hard-coded or additional undocumented accounts or keys, code obfuscation, undocumented binary blobs, rootkits, or anti-debugging, insecure debugging features, or otherwise out of date, insecure, or hidden functionality that could be used maliciously if discovered.
- Applicable: false
- ASVS ID: 10.2.3
- CWE: 507
- L1: Not required
- L2: Not required
- L3: Required
- L3 Text: ✓
- Ordinal: 3
- Type: Requirement

#### ASVS-342 (ASVS Object Type)
Verify that the application source code and third party libraries do not contain time bombs by searching for date and time related functions.
- Applicable: false
- ASVS ID: 10.2.4
- CWE: 511
- L1: Not required
- L2: Not required
- L3: Required
- L3 Text: ✓
- Ordinal: 4
- Type: Requirement

#### ASVS-343 (ASVS Object Type)
Verify that the application source code and third party libraries do not contain malicious code, such as salami attacks, logic bypasses, or logic bombs.
- Applicable: false
- ASVS ID: 10.2.5
- CWE: 511
- L1: Not required
- L2: Not required
- L3: Required
- L3 Text: ✓
- Ordinal: 5
- Type: Requirement

#### ASVS-344 (ASVS Object Type)
Verify that the application source code and third party libraries do not contain Easter eggs or any other potentially unwanted functionality.
- Applicable: false
- ASVS ID: 10.2.6
- CWE: 507
- L1: Not required
- L2: Not required
- L3: Required
- L3 Text: ✓
- Ordinal: 6
- Type: Requirement

### ASVS-345: Application Integrity (ASVS Object Type)
- ASVS ID: 10.3
- Ordinal: 3
- Type: Section

#### ASVS-346 (ASVS Object Type)
Verify that if the application has a client or server auto-update feature, updates should be obtained over secure channels and digitally signed. The update code must validate the digital signature of the update before installing or executing the update.
- Applicable: false
- ASVS ID: 10.3.1
- CWE: 16
- L1: Required
- L1 Text: ✓
- L2: Required
- L2 Text: ✓
- L3: Required
- L3 Text: ✓
- Ordinal: 1
- Type: Requirement

#### ASVS-347 (ASVS Object Type)
Verify that the application employs integrity protections, such as code signing or subresource integrity. The application must not load or execute code from untrusted sources, such as loading includes, modules, plugins, code, or libraries from untrusted sources or the Internet.
- Applicable: true
- ASVS ID: 10.3.2
- CWE: 353
- L1: Required
- L1 Text: ✓
- L2: Required
- L2 Text: ✓
- L3: Required
- L3 Text: ✓
- Ordinal: 2
- Type: Requirement

#### ASVS-348 (ASVS Object Type)
Verify that the application has protection from subdomain takeovers if the application relies upon DNS entries or DNS subdomains, such as expired domain names, out of date DNS pointers or CNAMEs, expired projects at public source code repos, or transient cloud APIs, serverless functions, or storage buckets (autogen-bucket-id.cloud.example.com) or similar. Protections can include ensuring that DNS names used by applications are regularly checked for expiry or change.
- Applicable: false
- ASVS ID: 10.3.3
- CWE: 350
- L1: Required
- L1 Text: ✓
- L2: Required
- L2 Text: ✓
- L3: Required
- L3 Text: ✓
- Ordinal: 3
- Type: Requirement

## ASVS-349: Business Logic (ASVS Object Type)
- ASVS ID: 11
- Ordinal: 11
- Type: Section

### ASVS-350: Business Logic Security (ASVS Object Type)
- ASVS ID: 11.1
- Ordinal: 1
- Type: Section

#### ASVS-351 (ASVS Object Type)
Verify that the application will only process business logic flows for the same user in sequential step order and without skipping steps.
- Applicable: false
- ASVS ID: 11.1.1
- CWE: 841
- L1: Required
- L1 Text: ✓
- L2: Required
- L2 Text: ✓
- L3: Required
- L3 Text: ✓
- Ordinal: 1
- Type: Requirement

#### ASVS-352 (ASVS Object Type)
Verify that the application will only process business logic flows with all steps being processed in realistic human time, i.e. transactions are not submitted too quickly.
- Applicable: false
- ASVS ID: 11.1.2
- CWE: 799
- L1: Required
- L1 Text: ✓
- L2: Required
- L2 Text: ✓
- L3: Required
- L3 Text: ✓
- Ordinal: 2
- Type: Requirement

#### ASVS-353 (ASVS Object Type)
Verify the application has appropriate limits for specific business actions or transactions which are correctly enforced on a per user basis.
- Applicable: false
- ASVS ID: 11.1.3
- CWE: 770
- L1: Required
- L1 Text: ✓
- L2: Required
- L2 Text: ✓
- L3: Required
- L3 Text: ✓
- Ordinal: 3
- Type: Requirement

#### ASVS-354 (ASVS Object Type)
Verify that the application has anti-automation controls to protect against excessive calls such as mass data exfiltration, business logic requests, file uploads or denial of service attacks.
- Applicable: false
- ASVS ID: 11.1.4
- CWE: 770
- L1: Required
- L1 Text: ✓
- L2: Required
- L2 Text: ✓
- L3: Required
- L3 Text: ✓
- Ordinal: 4
- Type: Requirement

#### ASVS-355 (ASVS Object Type)
Verify the application has business logic limits or validation to protect against likely business risks or threats, identified using threat modeling or similar methodologies.
- Applicable: false
- ASVS ID: 11.1.5
- CWE: 841
- L1: Required
- L1 Text: ✓
- L2: Required
- L2 Text: ✓
- L3: Required
- L3 Text: ✓
- Ordinal: 5
- Type: Requirement

#### ASVS-356 (ASVS Object Type)
Verify that the application does not suffer from "Time Of Check to Time Of Use" (TOCTOU) issues or other race conditions for sensitive operations.
- Applicable: false
- ASVS ID: 11.1.6
- CWE: 367
- L1: Not required
- L2: Required
- L2 Text: ✓
- L3: Required
- L3 Text: ✓
- Ordinal: 6
- Type: Requirement

#### ASVS-357 (ASVS Object Type)
Verify that the application monitors for unusual events or activity from a business logic perspective. For example, attempts to perform actions out of order or actions which a normal user would never attempt. (C9)
- Applicable: false
- ASVS ID: 11.1.7
- CWE: 754
- L1: Not required
- L2: Required
- L2 Text: ✓
- L3: Required
- L3 Text: ✓
- Ordinal: 7
- Type: Requirement

#### ASVS-358 (ASVS Object Type)
Verify that the application has configurable alerting when automated attacks or unusual activity is detected.
- Applicable: false
- ASVS ID: 11.1.8
- CWE: 390
- L1: Not required
- L2: Required
- L2 Text: ✓
- L3: Required
- L3 Text: ✓
- Ordinal: 8
- Type: Requirement

## ASVS-359: Files and Resources (ASVS Object Type)
- ASVS ID: 12
- Ordinal: 12
- Type: Section

### ASVS-360: File Upload (ASVS Object Type)
- ASVS ID: 12.1
- Ordinal: 1
- Type: Section

#### ASVS-361 (ASVS Object Type)
Verify that the application will not accept large files that could fill up storage or cause a denial of service.
- Applicable: false
- ASVS ID: 12.1.1
- CWE: 400
- L1: Required
- L1 Text: ✓
- L2: Required
- L2 Text: ✓
- L3: Required
- L3 Text: ✓
- Ordinal: 1
- Type: Requirement

#### ASVS-362 (ASVS Object Type)
Verify that the application checks compressed files (e.g. zip, gz, docx, odt) against maximum allowed uncompressed size and against maximum number of files before uncompressing the file.
- Applicable: false
- ASVS ID: 12.1.2
- CWE: 409
- L1: Not required
- L2: Required
- L2 Text: ✓
- L3: Required
- L3 Text: ✓
- Ordinal: 2
- Type: Requirement

#### ASVS-363 (ASVS Object Type)
Verify that a file size quota and maximum number of files per user is enforced to ensure that a single user cannot fill up the storage with too many files, or excessively large files.
- Applicable: false
- ASVS ID: 12.1.3
- CWE: 770
- L1: Not required
- L2: Required
- L2 Text: ✓
- L3: Required
- L3 Text: ✓
- Ordinal: 3
- Type: Requirement

### ASVS-364: File Integrity (ASVS Object Type)
- ASVS ID: 12.2
- Ordinal: 2
- Type: Section

#### ASVS-365 (ASVS Object Type)
Verify that files obtained from untrusted sources are validated to be of expected type based on the file's content.
- Applicable: false
- ASVS ID: 12.2.1
- CWE: 434
- L1: Not required
- L2: Required
- L2 Text: ✓
- L3: Required
- L3 Text: ✓
- Ordinal: 1
- Type: Requirement

### ASVS-366: File Execution (ASVS Object Type)
- ASVS ID: 12.3
- Ordinal: 3
- Type: Section

#### ASVS-367 (ASVS Object Type)
Verify that user-submitted filename metadata is not used directly by system or framework filesystems and that a URL API is used to protect against path traversal.
- Applicable: false
- ASVS ID: 12.3.1
- CWE: 22
- L1: Required
- L1 Text: ✓
- L2: Required
- L2 Text: ✓
- L3: Required
- L3 Text: ✓
- Ordinal: 1
- Type: Requirement

#### ASVS-368 (ASVS Object Type)
Verify that user-submitted filename metadata is validated or ignored to prevent the disclosure, creation, updating or removal of local files (LFI).
- Applicable: false
- ASVS ID: 12.3.2
- CWE: 73
- L1: Required
- L1 Text: ✓
- L2: Required
- L2 Text: ✓
- L3: Required
- L3 Text: ✓
- Ordinal: 2
- Type: Requirement

#### ASVS-369 (ASVS Object Type)
Verify that user-submitted filename metadata is validated or ignored to prevent the disclosure or execution of remote files via Remote File Inclusion (RFI) or Server-side Request Forgery (SSRF) attacks.
- Applicable: false
- ASVS ID: 12.3.3
- CWE: 98
- L1: Required
- L1 Text: ✓
- L2: Required
- L2 Text: ✓
- L3: Required
- L3 Text: ✓
- Ordinal: 3
- Type: Requirement

#### ASVS-370 (ASVS Object Type)
Verify that the application protects against Reflective File Download (RFD) by validating or ignoring user-submitted filenames in a JSON, JSONP, or URL parameter, the response Content-Type header should be set to text/plain, and the Content-Disposition header should have a fixed filename.
- Applicable: false
- ASVS ID: 12.3.4
- CWE: 641
- L1: Required
- L1 Text: ✓
- L2: Required
- L2 Text: ✓
- L3: Required
- L3 Text: ✓
- Ordinal: 4
- Type: Requirement

#### ASVS-371 (ASVS Object Type)
Verify that untrusted file metadata is not used directly with system API or libraries, to protect against OS command injection.
- Applicable: false
- ASVS ID: 12.3.5
- CWE: 78
- L1: Required
- L1 Text: ✓
- L2: Required
- L2 Text: ✓
- L3: Required
- L3 Text: ✓
- Ordinal: 5
- Type: Requirement

#### ASVS-372 (ASVS Object Type)
Verify that the application does not include and execute functionality from untrusted sources, such as unverified content distribution networks, JavaScript libraries, node npm libraries, or server-side DLLs.
- Applicable: false
- ASVS ID: 12.3.6
- CWE: 829
- L1: Not required
- L2: Required
- L2 Text: ✓
- L3: Required
- L3 Text: ✓
- Ordinal: 6
- Type: Requirement

### ASVS-373: File Storage (ASVS Object Type)
- ASVS ID: 12.4
- Ordinal: 4
- Type: Section

#### ASVS-374 (ASVS Object Type)
Verify that files obtained from untrusted sources are stored outside the web root, with limited permissions.
- Applicable: false
- ASVS ID: 12.4.1
- CWE: 552
- L1: Required
- L1 Text: ✓
- L2: Required
- L2 Text: ✓
- L3: Required
- L3 Text: ✓
- Ordinal: 1
- Type: Requirement

#### ASVS-375 (ASVS Object Type)
Verify that files obtained from untrusted sources are scanned by antivirus scanners to prevent upload and serving of known malicious content.
- Applicable: false
- ASVS ID: 12.4.2
- CWE: 509
- L1: Required
- L1 Text: ✓
- L2: Required
- L2 Text: ✓
- L3: Required
- L3 Text: ✓
- Ordinal: 2
- Type: Requirement

### ASVS-376: File Download (ASVS Object Type)
- ASVS ID: 12.5
- Ordinal: 5
- Type: Section

#### ASVS-377 (ASVS Object Type)
Verify that the web tier is configured to serve only files with specific file extensions to prevent unintentional information and source code leakage. For example, backup files (e.g. .bak), temporary working files (e.g. .swp), compressed files (.zip, .tar.gz, etc) and other extensions commonly used by editors should be blocked unless required.
- Applicable: false
- ASVS ID: 12.5.1
- CWE: 552
- L1: Required
- L1 Text: ✓
- L2: Required
- L2 Text: ✓
- L3: Required
- L3 Text: ✓
- Ordinal: 1
- Type: Requirement

#### ASVS-378 (ASVS Object Type)
Verify that direct requests to uploaded files will never be executed as HTML/JavaScript content.
- Applicable: false
- ASVS ID: 12.5.2
- CWE: 434
- L1: Required
- L1 Text: ✓
- L2: Required
- L2 Text: ✓
- L3: Required
- L3 Text: ✓
- Ordinal: 2
- Type: Requirement

### ASVS-379: SSRF Protection (ASVS Object Type)
- ASVS ID: 12.6
- Ordinal: 6
- Type: Section

#### ASVS-380 (ASVS Object Type)
Verify that the web or application server is configured with an allow list of resources or systems to which the server can send requests or load data/files from.
- Applicable: false
- ASVS ID: 12.6.1
- CWE: 918
- L1: Required
- L1 Text: ✓
- L2: Required
- L2 Text: ✓
- L3: Required
- L3 Text: ✓
- Ordinal: 1
- Type: Requirement

## ASVS-381: API and Web Service (ASVS Object Type)
- ASVS ID: 13
- Ordinal: 13
- Type: Section

### ASVS-382: Generic Web Service Security (ASVS Object Type)
- ASVS ID: 13.1
- Ordinal: 1
- Type: Section

#### ASVS-383 (ASVS Object Type)
Verify that all application components use the same encodings and parsers to avoid parsing attacks that exploit different URI or file parsing behavior that could be used in SSRF and RFI attacks.
- Applicable: false
- ASVS ID: 13.1.1
- CWE: 116
- L1: Required
- L1 Text: ✓
- L2: Required
- L2 Text: ✓
- L3: Required
- L3 Text: ✓
- Ordinal: 1
- Type: Requirement

#### ASVS-385 (ASVS Object Type)
Verify API URLs do not expose sensitive information, such as the API key, session tokens etc.
- Applicable: false
- ASVS ID: 13.1.3
- CWE: 598
- L1: Required
- L1 Text: ✓
- L2: Required
- L2 Text: ✓
- L3: Required
- L3 Text: ✓
- Ordinal: 3
- Type: Requirement

#### ASVS-386 (ASVS Object Type)
Verify that authorization decisions are made at both the URI, enforced by programmatic or declarative security at the controller or router, and at the resource level, enforced by model-based permissions.
- Applicable: false
- ASVS ID: 13.1.4
- CWE: 285
- L1: Not required
- L2: Required
- L2 Text: ✓
- L3: Required
- L3 Text: ✓
- Ordinal: 4
- Type: Requirement

#### ASVS-387 (ASVS Object Type)
Verify that requests containing unexpected or missing content types are rejected with appropriate headers (HTTP response status 406 Unacceptable or 415 Unsupported Media Type).
- Applicable: false
- ASVS ID: 13.1.5
- CWE: 434
- L1: Not required
- L2: Required
- L2 Text: ✓
- L3: Required
- L3 Text: ✓
- Ordinal: 5
- Type: Requirement

### ASVS-388: RESTful Web Service (ASVS Object Type)
- ASVS ID: 13.2
- Ordinal: 2
- Type: Section

#### ASVS-389 (ASVS Object Type)
Verify that enabled RESTful HTTP methods are a valid choice for the user or action, such as preventing normal users using DELETE or PUT on protected API or resources.
- Applicable: false
- ASVS ID: 13.2.1
- CWE: 650
- L1: Required
- L1 Text: ✓
- L2: Required
- L2 Text: ✓
- L3: Required
- L3 Text: ✓
- Ordinal: 1
- Type: Requirement

#### ASVS-390 (ASVS Object Type)
Verify that JSON schema validation is in place and verified before accepting input.
- Applicable: false
- ASVS ID: 13.2.2
- CWE: 20
- L1: Required
- L1 Text: ✓
- L2: Required
- L2 Text: ✓
- L3: Required
- L3 Text: ✓
- Ordinal: 2
- Type: Requirement

#### ASVS-391 (ASVS Object Type)
Verify that RESTful web services that utilize cookies are protected from Cross-Site Request Forgery via the use of at least one or more of the following: double submit cookie pattern, CSRF nonces, or Origin request header checks.
- Applicable: false
- ASVS ID: 13.2.3
- CWE: 352
- L1: Required
- L1 Text: ✓
- L2: Required
- L2 Text: ✓
- L3: Required
- L3 Text: ✓
- Ordinal: 3
- Type: Requirement

#### ASVS-393 (ASVS Object Type)
Verify that REST services explicitly check the incoming Content-Type to be the expected one, such as application/xml or application/json.
- Applicable: false
- ASVS ID: 13.2.5
- CWE: 436
- L1: Not required
- L2: Required
- L2 Text: ✓
- L3: Required
- L3 Text: ✓
- Ordinal: 5
- Type: Requirement

#### ASVS-394 (ASVS Object Type)
Verify that the message headers and payload are trustworthy and not modified in transit. Requiring strong encryption for transport (TLS only) may be sufficient in many cases as it provides both confidentiality and integrity protection. Per-message digital signatures can provide additional assurance on top of the transport protections for high-security applications but bring with them additional complexity and risks to weigh against the benefits.
- Applicable: false
- ASVS ID: 13.2.6
- CWE: 345
- L1: Not required
- L2: Required
- L2 Text: ✓
- L3: Required
- L3 Text: ✓
- Ordinal: 6
- Type: Requirement

### ASVS-395: SOAP Web Service (ASVS Object Type)
- ASVS ID: 13.3
- Ordinal: 3
- Type: Section

#### ASVS-396 (ASVS Object Type)
Verify that XSD schema validation takes place to ensure a properly formed XML document, followed by validation of each input field before any processing of that data takes place.
- Applicable: false
- ASVS ID: 13.3.1
- CWE: 20
- L1: Required
- L1 Text: ✓
- L2: Required
- L2 Text: ✓
- L3: Required
- L3 Text: ✓
- Ordinal: 1
- Type: Requirement

#### ASVS-397 (ASVS Object Type)
Verify that the message payload is signed using WS-Security to ensure reliable transport between client and service.
- Applicable: false
- ASVS ID: 13.3.2
- CWE: 345
- L1: Not required
- L2: Required
- L2 Text: ✓
- L3: Required
- L3 Text: ✓
- Ordinal: 2
- Type: Requirement

### ASVS-398: GraphQL (ASVS Object Type)
- ASVS ID: 13.4
- Ordinal: 4
- Type: Section

#### ASVS-399 (ASVS Object Type)
Verify that a query allow list or a combination of depth limiting and amount limiting is used to prevent GraphQL or data layer expression Denial of Service (DoS) as a result of expensive, nested queries. For more advanced scenarios, query cost analysis should be used.
- Applicable: false
- ASVS ID: 13.4.1
- CWE: 770
- L1: Not required
- L2: Required
- L2 Text: ✓
- L3: Required
- L3 Text: ✓
- Ordinal: 1
- Type: Requirement

#### ASVS-400 (ASVS Object Type)
Verify that GraphQL or other data layer authorization logic should be implemented at the business logic layer instead of the GraphQL layer.
- Applicable: false
- ASVS ID: 13.4.2
- CWE: 285
- L1: Not required
- L2: Required
- L2 Text: ✓
- L3: Required
- L3 Text: ✓
- Ordinal: 2
- Type: Requirement

## ASVS-401: Configuration (ASVS Object Type)
- ASVS ID: 14
- Ordinal: 14
- Type: Section

### ASVS-402: Build and Deploy (ASVS Object Type)
- ASVS ID: 14.1
- Ordinal: 1
- Type: Section

#### ASVS-403 (ASVS Object Type)
Verify that the application build and deployment processes are performed in a secure and repeatable way, such as CI / CD automation, automated configuration management, and automated deployment scripts.
- Applicable: true
- ASVS ID: 14.1.1
- L1: Not required
- L2: Required
- L2 Text: ✓
- L3: Required
- L3 Text: ✓
- Ordinal: 1
- Type: Requirement

#### ASVS-404 (ASVS Object Type)
Verify that compiler flags are configured to enable all available buffer overflow protections and warnings, including stack randomization, data execution prevention, and to break the build if an unsafe pointer, memory, format string, integer, or string operations are found.
- Applicable: false
- ASVS ID: 14.1.2
- CWE: 120
- L1: Not required
- L2: Required
- L2 Text: ✓
- L3: Required
- L3 Text: ✓
- Ordinal: 2
- Type: Requirement

#### ASVS-405 (ASVS Object Type)
Verify that server configuration is hardened as per the recommendations of the application server and frameworks in use.
- Applicable: false
- ASVS ID: 14.1.3
- CWE: 16
- L1: Not required
- L2: Required
- L2 Text: ✓
- L3: Required
- L3 Text: ✓
- Ordinal: 3
- Type: Requirement

#### ASVS-406 (ASVS Object Type)
Verify that the application, configuration, and all dependencies can be re-deployed using automated deployment scripts, built from a documented and tested runbook in a reasonable time, or restored from backups in a timely fashion.
- Applicable: true
- ASVS ID: 14.1.4
- L1: Not required
- L2: Required
- L2 Text: ✓
- L3: Required
- L3 Text: ✓
- Ordinal: 4
- Type: Requirement

#### ASVS-407 (ASVS Object Type)
Verify that authorized administrators can verify the integrity of all security-relevant configurations to detect tampering.
- Applicable: true
- ASVS ID: 14.1.5
- L1: Not required
- L2: Not required
- L3: Required
- L3 Text: ✓
- Ordinal: 5
- Type: Requirement

### ASVS-408: Dependency (ASVS Object Type)
- ASVS ID: 14.2
- Ordinal: 2
- Type: Section

#### ASVS-409 (ASVS Object Type)
Verify that all components are up to date, preferably using a dependency checker during build or compile time. (C2)
- Applicable: true
- ASVS ID: 14.2.1
- CWE: 1026
- L1: Required
- L1 Text: ✓
- L2: Required
- L2 Text: ✓
- L3: Required
- L3 Text: ✓
- Ordinal: 1
- Type: Requirement

#### ASVS-410 (ASVS Object Type)
Verify that all unneeded features, documentation, sample applications and configurations are removed.
- Applicable: true
- ASVS ID: 14.2.2
- CWE: 1002
- L1: Required
- L1 Text: ✓
- L2: Required
- L2 Text: ✓
- L3: Required
- L3 Text: ✓
- Ordinal: 2
- Type: Requirement

#### ASVS-411 (ASVS Object Type)
Verify that if application assets, such as JavaScript libraries, CSS or web fonts, are hosted externally on a Content Delivery Network (CDN) or external provider, Subresource Integrity (SRI) is used to validate the integrity of the asset.
- Applicable: false
- ASVS ID: 14.2.3
- CWE: 829
- L1: Required
- L1 Text: ✓
- L2: Required
- L2 Text: ✓
- L3: Required
- L3 Text: ✓
- Ordinal: 3
- Type: Requirement

#### ASVS-412 (ASVS Object Type)
Verify that third party components come from pre-defined, trusted and continually maintained repositories. (C2)
- Applicable: false
- ASVS ID: 14.2.4
- CWE: 829
- L1: Not required
- L2: Required
- L2 Text: ✓
- L3: Required
- L3 Text: ✓
- Ordinal: 4
- Type: Requirement

#### ASVS-413 (ASVS Object Type)
Verify that a Software Bill of Materials (SBOM) is maintained of all third party libraries in use. (C2)
- Applicable: false
- ASVS ID: 14.2.5
- L1: Not required
- L2: Required
- L2 Text: ✓
- L3: Required
- L3 Text: ✓
- Ordinal: 5
- Type: Requirement

#### ASVS-414 (ASVS Object Type)
Verify that the attack surface is reduced by sandboxing or encapsulating third party libraries to expose only the required behaviour into the application. (C2)
- Applicable: false
- ASVS ID: 14.2.6
- CWE: 265
- L1: Not required
- L2: Required
- L2 Text: ✓
- L3: Required
- L3 Text: ✓
- Ordinal: 6
- Type: Requirement

### ASVS-415: Unintended Security Disclosure (ASVS Object Type)
- ASVS ID: 14.3
- Ordinal: 3
- Type: Section

#### ASVS-417 (ASVS Object Type)
Verify that web or application server and application framework debug modes are disabled in production to eliminate debug features, developer consoles, and unintended security disclosures.
- Applicable: false
- ASVS ID: 14.3.2
- CWE: 497
- L1: Required
- L1 Text: ✓
- L2: Required
- L2 Text: ✓
- L3: Required
- L3 Text: ✓
- Ordinal: 2
- Type: Requirement

#### ASVS-418 (ASVS Object Type)
Verify that the HTTP headers or any part of the HTTP response do not expose detailed version information of system components.
- Applicable: false
- ASVS ID: 14.3.3
- CWE: 200
- L1: Required
- L1 Text: ✓
- L2: Required
- L2 Text: ✓
- L3: Required
- L3 Text: ✓
- Ordinal: 3
- Type: Requirement

### ASVS-419: HTTP Security Headers (ASVS Object Type)
- ASVS ID: 14.4
- Ordinal: 4
- Type: Section

#### ASVS-420 (ASVS Object Type)
Verify that every HTTP response contains a Content-Type header. Also specify a safe character set (e.g., UTF-8, ISO-8859-1) if the content types are text/*, /+xml and application/xml. Content must match with the provided Content-Type header.
- Applicable: false
- ASVS ID: 14.4.1
- CWE: 173
- L1: Required
- L1 Text: ✓
- L2: Required
- L2 Text: ✓
- L3: Required
- L3 Text: ✓
- Ordinal: 1
- Type: Requirement

#### ASVS-421 (ASVS Object Type)
Verify that all API responses contain a Content-Disposition: attachment; filename="api.json" header (or other appropriate filename for the content type).
- Applicable: false
- ASVS ID: 14.4.2
- CWE: 116
- L1: Required
- L1 Text: ✓
- L2: Required
- L2 Text: ✓
- L3: Required
- L3 Text: ✓
- Ordinal: 2
- Type: Requirement

#### ASVS-422 (ASVS Object Type)
Verify that a Content Security Policy (CSP) response header is in place that helps mitigate impact for XSS attacks like HTML, DOM, JSON, and JavaScript injection vulnerabilities.
- Applicable: false
- ASVS ID: 14.4.3
- CWE: 1021
- L1: Required
- L1 Text: ✓
- L2: Required
- L2 Text: ✓
- L3: Required
- L3 Text: ✓
- Ordinal: 3
- Type: Requirement

#### ASVS-423 (ASVS Object Type)
Verify that all responses contain a X-Content-Type-Options: nosniff header.
- Applicable: false
- ASVS ID: 14.4.4
- CWE: 116
- L1: Required
- L1 Text: ✓
- L2: Required
- L2 Text: ✓
- L3: Required
- L3 Text: ✓
- Ordinal: 4
- Type: Requirement

#### ASVS-424 (ASVS Object Type)
Verify that a Strict-Transport-Security header is included on all responses and for all subdomains, such as Strict-Transport-Security: max-age=15724800; includeSubdomains.
- Applicable: false
- ASVS ID: 14.4.5
- CWE: 523
- L1: Required
- L1 Text: ✓
- L2: Required
- L2 Text: ✓
- L3: Required
- L3 Text: ✓
- Ordinal: 5
- Type: Requirement

#### ASVS-425 (ASVS Object Type)
Verify that a suitable Referrer-Policy header is included to avoid exposing sensitive information in the URL through the Referer header to untrusted parties.
- Applicable: false
- ASVS ID: 14.4.6
- CWE: 116
- L1: Required
- L1 Text: ✓
- L2: Required
- L2 Text: ✓
- L3: Required
- L3 Text: ✓
- Ordinal: 6
- Type: Requirement

#### ASVS-426 (ASVS Object Type)
Verify that the content of a web application cannot be embedded in a third-party site by default and that embedding of the exact resources is only allowed where necessary by using suitable Content-Security-Policy: frame-ancestors and X-Frame-Options response headers.
- Applicable: false
- ASVS ID: 14.4.7
- CWE: 1021
- L1: Required
- L1 Text: ✓
- L2: Required
- L2 Text: ✓
- L3: Required
- L3 Text: ✓
- Ordinal: 7
- Type: Requirement

### ASVS-427: HTTP Request Header Validation (ASVS Object Type)
- ASVS ID: 14.5
- Ordinal: 5
- Type: Section

#### ASVS-428 (ASVS Object Type)
Verify that the application server only accepts the HTTP methods in use by the application/API, including pre-flight OPTIONS, and logs/alerts on any requests that are not valid for the application context.
- Applicable: false
- ASVS ID: 14.5.1
- CWE: 749
- L1: Required
- L1 Text: ✓
- L2: Required
- L2 Text: ✓
- L3: Required
- L3 Text: ✓
- Ordinal: 1
- Type: Requirement

#### ASVS-429 (ASVS Object Type)
Verify that the supplied Origin header is not used for authentication or access control decisions, as the Origin header can easily be changed by an attacker.
- Applicable: false
- ASVS ID: 14.5.2
- CWE: 346
- L1: Required
- L1 Text: ✓
- L2: Required
- L2 Text: ✓
- L3: Required
- L3 Text: ✓
- Ordinal: 2
- Type: Requirement

#### ASVS-430 (ASVS Object Type)
Verify that the Cross-Origin Resource Sharing (CORS) Access-Control-Allow-Origin header uses a strict allow list of trusted domains and subdomains to match against and does not support the "null" origin.
- Applicable: false
- ASVS ID: 14.5.3
- CWE: 346
- L1: Required
- L1 Text: ✓
- L2: Required
- L2 Text: ✓
- L3: Required
- L3 Text: ✓
- Ordinal: 3
- Type: Requirement

#### ASVS-431 (ASVS Object Type)
Verify that HTTP headers added by a trusted proxy or SSO devices, such as a bearer token, are authenticated by the application.
- Applicable: false
- ASVS ID: 14.5.4
- CWE: 306
- L1: Not required
- L2: Required
- L2 Text: ✓
- L3: Required
- L3 Text: ✓
- Ordinal: 4
- Type: Requirement

# Specification: RISKS
- ReqIF.Description: Failure Mode and Effects Analysis

## RISKS-2: Risks (RISKS Object Type)
- Type: Section

### RISKS-43: Application (RISKS Object Type)
- Type: Section

#### RISKS-8 (RISKS Object Type)
Application is reliable
- Type: Requirement

##### RISKS-22 (RISKS Object Type)
Loss of data entered by users
- Potential Effects: Users stop using the application
- SEV: 6
- Type: Requirement

###### RISKS-40 (RISKS Object Type)
The application crashes due to a bug
- DET: 8
- Detection Mode: Stability test of the application with corner case data.
- PROB: 3
- SEV: 6
- Type: Requirement

###### RISKS-26 (RISKS Object Type)
Implement Autosave functionality storing immediately all changes into a persistent application storage so that only the last unsaved change is lost.
- DET: 8
- PROB: 3
- Responsibility: Libor Bus
- SEV: 2
- Target Date: 2015-12-31T00:00:00.000Z
- Type: Requirement

###### RISKS-44 (RISKS Object Type)
Functional bug in user data handling
- DET: 4
- Detection Mode: Unit tests of user data handling with 90% coverage.
- PROB: 3
- SEV: 6
- Type: Requirement

###### RISKS-45 (RISKS Object Type)
Unit tests with 99% coverage
- DET: 1
- PROB: 3
- Responsibility: Libor Bus
- SEV: 6
- Target Date: 2018-09-30T00:00:00.000Z
- Type: Requirement

# Specification: SRS
- ReqIF.Description: ReqView Software Requirements Specification

## SRS-20: Requirements (SRS Object Type)
- Type: Section

### SRS-21: External interfaces (SRS Object Type)
- Type: Section

### SRS-22: Functions (SRS Object Type)
- Type: Section

#### SRS-51: File Operations (SRS Object Type)
- Type: Section

##### SRS-52: Create Document (SRS Object Type)
- Type: Section

###### SRS-53 (SRS Object Type)
The application shall allow users to create a new empty document.
- Status: Released
- Type: Requirement
- Ver. Method: Test
- Satisfaction -> NEEDS-58

###### SRS-54 (SRS Object Type)
If the current document contains unsaved changes then the application shall allow users to save the changes before closing the document.
- Status: Released
- Type: Requirement
- Ver. Method: Test
- Satisfaction -> NEEDS-58

##### SRS-55: Open File (SRS Object Type)
- Type: Section

###### SRS-56 (SRS Object Type)
The application shall allow users to open a document from a chosen file.
- Status: Released
- Type: Requirement
- Ver. Method: Test
- Satisfaction -> NEEDS-58

##### SRS-58: Save Local File (SRS Object Type)
- Type: Section

###### SRS-59 (SRS Object Type)
The application shall allow users to save the opened document into a file.
- Status: Released
- Type: Requirement
- Ver. Method: Test
- Satisfaction -> NEEDS-58

##### SRS-60: Document Template (SRS Object Type)
- Type: Section

###### SRS-61 (SRS Object Type)
The application shall allow users to create a document template file from the opened document.
- Status: Released
- Type: Requirement
- Ver. Method: Test
- Satisfaction -> NEEDS-14

###### SRS-62 (SRS Object Type)
Document templates shall store structure of document sections and definition and values of requirement attributes.
- Status: Released
- Type: Requirement
- Ver. Method: Test
- Satisfaction -> NEEDS-14

###### SRS-63 (SRS Object Type)
The application shall allow users to create a new document from a chosen document template file preserving the structure of document sections and the definition and values of requirement attributes.
- Status: Released
- Type: Requirement
- Ver. Method: Test
- Satisfaction -> NEEDS-14

##### SRS-71: Import (SRS Object Type)
- Type: Section

###### SRS-72 (SRS Object Type)
The application shall allow users to import a MS Word document preserving structure of document sections and paragraphs, rich text description of requirements and images.
- Status: Released
- Type: Requirement
- Ver. Method: Test
- Satisfaction -> NEEDS-27

###### SRS-73 (SRS Object Type)
The application shall allow users to import a MS Excel table of requirements preserving section headings, levels, unformatted text description of requirements and values of custom attributes.
- Status: Released
- Type: Requirement
- Ver. Method: Test
- Satisfaction -> NEEDS-71

##### SRS-74: Export (SRS Object Type)
- Type: Section

###### SRS-76 (SRS Object Type)
The application shall allow users to export the displayed document view to HTML.
- Status: Released
- Type: Requirement
- Ver. Method: Test
- Satisfaction -> NEEDS-23
- Satisfaction -> NEEDS-28

###### SRS-77 (SRS Object Type)
The application shall allow users to export requirements to CSV.
- Status: Released
- Type: Requirement
- Ver. Method: Test
- Satisfaction -> NEEDS-23
- Satisfaction -> NEEDS-72

#### SRS-78: Document View (SRS Object Type)
- Type: Section

##### SRS-79: Table of Contents (SRS Object Type)
- Type: Section

###### SRS-80 (SRS Object Type)
The application shall display the table of contents containing section headings organized according to their document tree hierarchy.
- Status: Released
- Type: Requirement
- Ver. Method: Test
- Satisfaction -> NEEDS-12

###### SRS-81 (SRS Object Type)
When user clicks on a document section in the table of contents then the application shall focus the section in the requirements table.
- Status: Released
- Type: Requirement
- Ver. Method: Test
- Satisfaction -> NEEDS-12

##### SRS-82: Requirements Table (SRS Object Type)
- Type: Section

###### SRS-83 (SRS Object Type)
The application shall display the document in a requirements table containing the following columns: ID, Description, Discussion, Links and a column for each custom requirement attribute.
- Status: Released
- Type: Requirement
- Ver. Method: Test
- Satisfaction -> NEEDS-12
- Satisfaction -> NEEDS-17
- Satisfaction -> NEEDS-32
- Satisfaction -> NEEDS-68
- Satisfaction -> NEEDS-73

###### SRS-84 (SRS Object Type)
The ID column of the requirements table shall display unique requirement identifiers.
- Status: Released
- Type: Requirement
- Ver. Method: Test
- Satisfaction -> NEEDS-32
- Satisfaction -> NEEDS-73

###### SRS-85 (SRS Object Type)
The Description column of the requirements table shall display the section numbers, headings, requirement text descriptions and attachments.
- Status: Released
- Type: Requirement
- Ver. Method: Test
- Satisfaction -> NEEDS-17
- Satisfaction -> NEEDS-68
- Satisfaction -> NEEDS-73

###### SRS-86 (SRS Object Type)
The Discussion column of the requirements table shall display requirement comments with information about comment author, date and text ordered by date and time.
- Status: Released
- Type: Requirement
- Ver. Method: Test
- Satisfaction -> NEEDS-24
- Satisfaction -> NEEDS-73

###### SRS-87 (SRS Object Type)
The Links column of the requirements table shall display requirement traceability links grouped by link types.
- Status: Released
- Type: Requirement
- Ver. Method: Test
- Satisfaction -> NEEDS-21
- Satisfaction -> NEEDS-30
- Satisfaction -> NEEDS-73

###### SRS-88 (SRS Object Type)
The application shall allow users to change width of each requirements table column.
- Status: Released
- Type: Requirement
- Ver. Method: Test
- Satisfaction -> NEEDS-73

###### SRS-190 (SRS Object Type)
The application shall allow users to reorder requirements table columns.
- Status: Released
- Type: Requirement
- Ver. Method: Test
- Satisfaction -> NEEDS-73

###### SRS-89 (SRS Object Type)
The application shall allow users to show and hide requirements table columns except the ID column.
- Status: Released
- Type: Requirement
- Ver. Method: Test
- Satisfaction -> NEEDS-73

###### SRS-90 (SRS Object Type)
The application shall allow users to sort all requirements table columns except the Discussion and Links columns by ascending or descending order.
- Status: Released
- Type: Requirement
- Ver. Method: Test
- Satisfaction -> NEEDS-35

##### SRS-91: Detailed Information (SRS Object Type)
- Type: Section

###### SRS-92 (SRS Object Type)
The application shall allow users to show and hide a pane displaying detailed information about custom attributes, discussion, traceability links or history of changes of the selected requirement.
- Status: Released
- Type: Requirement
- Ver. Method: Test
- Satisfaction -> NEEDS-30
- Satisfaction -> NEEDS-74

###### SRS-93 (SRS Object Type)
While the custom attributes pane is shown, the application shall display values of all assigned custom attributes for the selected requirement.
- Status: Released
- Type: Requirement
- Ver. Method: Test
- Satisfaction -> NEEDS-74

###### SRS-94 (SRS Object Type)
While the discussion pane is shown, the application shall display all comments for the selected requirement ordered by date and time.
- Status: Released
- Type: Requirement
- Ver. Method: Test
- Satisfaction -> NEEDS-74

###### SRS-96 (SRS Object Type)
While the discussion pane is shown, the application shall allow users to expand or collapse a selected comment or all displayed comments.
- Status: Released
- Type: Requirement
- Ver. Method: Test
- Satisfaction -> NEEDS-74

###### SRS-97 (SRS Object Type)
While a displayed discussion comment is expanded, then the application shall display the date, time, author and description of the comment.
- Status: Released
- Type: Requirement
- Ver. Method: Test
- Satisfaction -> NEEDS-74

###### SRS-98 (SRS Object Type)
While a displayed discussion comment is collapsed, then the application shall display the date, time and author of the comment.
- Status: Released
- Type: Requirement
- Ver. Method: Test
- Satisfaction -> NEEDS-74

###### SRS-99 (SRS Object Type)
While the links pane is shown, the application shall display all traceability links starting in or leading to the selected requirement grouped by link types and ordered by ID of the linked object.
- Status: Released
- Type: Requirement
- Ver. Method: Test
- Satisfaction -> NEEDS-30
- Satisfaction -> NEEDS-74

###### SRS-142 (SRS Object Type)
When user clicks on a traceability link then the application shall focus the linked requirement.
- Status: Released
- Type: Requirement
- Ver. Method: Test
- Satisfaction -> NEEDS-21
- Satisfaction -> NEEDS-30
- Satisfaction -> NEEDS-74

#### SRS-104: Edit Document (SRS Object Type)
- Type: Section

##### SRS-105: Document Structure (SRS Object Type)
- Type: Section

###### SRS-106 (SRS Object Type)
The application shall allow users to create a new requirement and place it in any document section.
- Status: Released
- Type: Requirement
- Ver. Method: Test
- Satisfaction -> NEEDS-12
- Satisfaction -> NEEDS-68

###### SRS-107 (SRS Object Type)
When users creates a new requirement the application shall assign it a unique ID which cannot be changed.
- Status: Released
- Type: Requirement
- Ver. Method: Test
- Satisfaction -> NEEDS-32

###### SRS-108 (SRS Object Type)
The application shall allow users to copy selected requirements or document sections within the document.
- Status: Released
- Type: Requirement
- Ver. Method: Test
- Satisfaction -> NEEDS-12

###### SRS-109 (SRS Object Type)
The application shall allow users to move selected requirements or document sections within the document.
- Status: Released
- Type: Requirement
- Ver. Method: Test
- Satisfaction -> NEEDS-12

###### SRS-110 (SRS Object Type)
The application shall allow users to mark selected requirements or document sections as deleted.
- Status: Released
- Type: Requirement
- Ver. Method: Test
- Satisfaction -> NEEDS-12

###### SRS-111 (SRS Object Type)
The application shall allow users to undelete selected deleted requirements or document sections.
- Status: Released
- Type: Requirement
- Ver. Method: Test
- Satisfaction -> NEEDS-12

###### SRS-112 (SRS Object Type)
The application shall allow users to permanently remove selected deleted requirements or document sections from the document.
- Status: Released
- Type: Requirement
- Ver. Method: Test
- Satisfaction -> NEEDS-12

##### SRS-113: Requirement Attributes (SRS Object Type)
- Type: Section

###### SRS-114 (SRS Object Type)
The application shall allow users to edit the heading of the selected section.
- Status: Released
- Type: Requirement
- Ver. Method: Test
- Satisfaction -> NEEDS-12

###### SRS-115 (SRS Object Type)
The application shall allow users to edit the text description of the selected requirement.
- Status: Released
- Type: Requirement
- Ver. Method: Test
- Satisfaction -> NEEDS-68

###### SRS-116 (SRS Object Type)
The application shall allow users to paste an HTML content copied from MS Word, Excel or other application into the text description of the selected requirement.
- Status: Released
- Type: Requirement
- Ver. Method: Test
- Satisfaction -> NEEDS-68

##### SRS-118: Custom Attributes (SRS Object Type)
- Type: Section

###### SRS-119 (SRS Object Type)
The application shall allow users to define custom requirement attributes and assign them a unique ID which cannot be changed.
- Status: Released
- Type: Requirement
- Ver. Method: Test
- Satisfaction -> NEEDS-19

###### SRS-121 (SRS Object Type)
The application shall allow users to set a type of each custom attribute as follows: boolean, integer number, real number, string, date, enum or XHTML.
- Status: Released
- Type: Requirement
- Ver. Method: Test
- Satisfaction -> NEEDS-19

###### SRS-191 (SRS Object Type)
The application shall allow users to set one or more values for custom attributes of enumeration type.
- Status: Released
- Type: Requirement
- Ver. Method: Test
- Satisfaction -> NEEDS-19

###### SRS-122 (SRS Object Type)
When a user changes the type of a custom attribute then the application shall automatically convert all values of the attribute to the new type.
- Status: Released
- Type: Requirement
- Ver. Method: Test
- Satisfaction -> NEEDS-19

###### SRS-157 (SRS Object Type)
If the automatic conversion fails for any attribute value, then the application shall prevent the change of custom attribute type.
- Status: Released
- Type: Requirement
- Ver. Method: Test
- Satisfaction -> NEEDS-19

###### SRS-120 (SRS Object Type)
The application shall allow users to set an optional name of each custom attribute.
- Status: Released
- Type: Requirement
- Ver. Method: Test
- Satisfaction -> NEEDS-19

###### SRS-192 (SRS Object Type)
The application shall allow users to remove custom attributes.
- Status: Released
- Type: Requirement
- Ver. Method: Test
- Satisfaction -> NEEDS-19

###### SRS-193 (SRS Object Type)
When a user removes a custom attribute then the application shall unset values of the attribute in all requirements.
- Status: Released
- Type: Requirement
- Ver. Method: Test
- Satisfaction -> NEEDS-19

###### SRS-165 (SRS Object Type)
The application shall allow users to edit custom attributes of the selected requirement.
- Status: Released
- Type: Requirement
- Ver. Method: Test
- Satisfaction -> NEEDS-69

##### SRS-123: Attachments (SRS Object Type)
- Type: Section

###### SRS-124 (SRS Object Type)
The application shall allow users to attach one or more images or documents (PDF, Word, Excel, Powerpoint, Visio, …) to the selected requirement.
- Status: Released
- Type: Requirement
- Ver. Method: Test
- Satisfaction -> NEEDS-17

###### SRS-126 (SRS Object Type)
When a new attachment is added to the document then the application shall generate its unique attachment ID as a combination of the requirement ID and the original attachment file name.
- Status: Released
- Type: Requirement
- Ver. Method: Test
- Satisfaction -> NEEDS-17

###### SRS-210 (SRS Object Type)
The application shall display preview of image attachments in the document.
- Status: Released
- Type: Requirement
- Ver. Method: Test
- Satisfaction -> NEEDS-17

###### SRS-127 (SRS Object Type)
The application shall allow users to save attachment files to the local file system.
- Status: Released
- Type: Requirement
- Ver. Method: Test
- Satisfaction -> NEEDS-17

###### SRS-128 (SRS Object Type)
The application shall allow users to update content of requirement attachments from a selected file.
- Status: Released
- Type: Requirement
- Ver. Method: Test
- Satisfaction -> NEEDS-17

###### SRS-129 (SRS Object Type)
The application shall allow users to permanently remove attachments from the document.
- Status: Released
- Type: Requirement
- Ver. Method: Test
- Satisfaction -> NEEDS-17

###### SRS-130 (SRS Object Type)
Example:
This is an example attachment.
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- Type: Information

##### SRS-131: Comments (SRS Object Type)
- Type: Section

###### SRS-132 (SRS Object Type)
The application shall allow users to comment the selected requirement.
- Status: Released
- Type: Requirement
- Ver. Method: Test
- Satisfaction -> NEEDS-24

###### SRS-133 (SRS Object Type)
When a user creates a new comment then the application shall record the current date and time and the author of the comment.
- Status: Released
- Type: Requirement
- Ver. Method: Test
- Satisfaction -> NEEDS-24

##### SRS-134: Traceability Links Configuration (SRS Object Type)
- Type: Section

###### SRS-135 (SRS Object Type)
The application shall allow users to define link types and assign them a unique ID which cannot be changed.
- Status: Released
- Type: Requirement
- Ver. Method: Test
- Satisfaction -> NEEDS-16

###### SRS-156 (SRS Object Type)
The application shall allow users to set for each link type its name and role name of the source and target requirements.
- Status: Released
- Type: Requirement
- Ver. Method: Test
- Satisfaction -> NEEDS-16

###### SRS-138 (SRS Object Type)
The application shall allow users to remove link types.
- Status: Released
- Type: Requirement
- Ver. Method: Test
- Satisfaction -> NEEDS-16

###### SRS-161 (SRS Object Type)
When a user removes a link type then the application shall remove all traceability links of the link type from the document.
- Status: Released
- Type: Requirement
- Ver. Method: Test
- Satisfaction -> NEEDS-16

##### SRS-136: Traceability Links (SRS Object Type)
- Type: Section

###### SRS-137 (SRS Object Type)
The application shall allow users to create directed traceability links of a chosen link type between selections of requirements or document sections.
- Status: Released
- Type: Requirement
- Ver. Method: Test
- Satisfaction -> NEEDS-21

###### SRS-139 (SRS Object Type)
The application shall allow users to change the link type of a selected link traceability.
- Status: Released
- Type: Requirement
- Ver. Method: Test
- Satisfaction -> NEEDS-21

###### SRS-140 (SRS Object Type)
The application shall allow users to revert direction of a selected traceability link.
- Status: Released
- Type: Requirement
- Ver. Method: Test
- Satisfaction -> NEEDS-21

###### SRS-141 (SRS Object Type)
The application shall allow users to permanently remove a selected traceability link from the document.
- Status: Released
- Type: Requirement
- Ver. Method: Test
- Satisfaction -> NEEDS-21

##### SRS-143: Auto Save (SRS Object Type)
- Type: Section

###### SRS-144 (SRS Object Type)
The application shall automatically persist all document changes and restore them when it is restarted.
- Status: Released
- Type: Requirement
- Ver. Method: Test
- Mitigation -> RISKS-26
- Satisfaction -> NEEDS-33

###### SRS-160 (SRS Object Type)
When user closes the document the application shall clear all persisted document data.
- Status: Released
- Type: Requirement
- Ver. Method: Test
- Mitigation -> RISKS-26
- Satisfaction -> NEEDS-33

#### SRS-145: Filtering (SRS Object Type)
- Type: Section

##### SRS-146: Requirements Filter (SRS Object Type)
- Type: Section

###### SRS-147 (SRS Object Type)
The application shall allow users to filter requirements according to a condition in disjunctive normal form (DNF).
- Status: Released
- Type: Requirement
- Ver. Method: Test
- Satisfaction -> NEEDS-34

###### SRS-148 (SRS Object Type)
The application shall allow users to enter a filtering condition matching document sections by their number or heading.
- Status: Released
- Type: Requirement
- Ver. Method: Test
- Satisfaction -> NEEDS-34

###### SRS-149 (SRS Object Type)
The application shall allow users to enter a filtering condition matching requirements by their text description or a custom attribute.
- Status: Released
- Type: Requirement
- Ver. Method: Test
- Satisfaction -> NEEDS-34

###### SRS-150 (SRS Object Type)
The application shall allow users to filter requirements with missing traceability links of a given type.
- Status: Released
- Type: Requirement
- Ver. Method: Test
- Satisfaction -> NEEDS-34

##### SRS-151: Full Text Search (SRS Object Type)
- Type: Section

###### SRS-152 (SRS Object Type)
The application shall allow users to search requirements matching one or more given keywords in an string or xhtml attribute.
- Status: Released
- Type: Requirement
- Ver. Method: Test
- Satisfaction -> NEEDS-36

###### SRS-153 (SRS Object Type)
While the search mode is active the application shall highlight the matched requirements and allow user to select the next or previous matched requirement in the document.
- Status: Released
- Type: Requirement
- Ver. Method: Test
- Satisfaction -> NEEDS-36

#### SRS-154: History of Changes (SRS Object Type)
- Type: Section

##### SRS-159 (SRS Object Type)
When a user changes a requirement the application shall record the current date and time and the author of the change.
- Status: Released
- Type: Requirement
- Ver. Method: Test
- Satisfaction -> NEEDS-26

##### SRS-101 (SRS Object Type)
The application shall display all changes of the selected requirement ordered by date and time.
- Status: Released
- Type: Requirement
- Ver. Method: Test
- Satisfaction -> NEEDS-26

##### SRS-102 (SRS Object Type)
Each displayed requirement change shall contain author, date & time and description of the change.
- Status: Released
- Type: Requirement
- Ver. Method: Test
- Satisfaction -> NEEDS-26

##### SRS-103 (SRS Object Type)
The application shall allow users to expand and collapse all changes in the History pane.
- Status: Released
- Type: Requirement
- Ver. Method: Test
- Satisfaction -> NEEDS-26

#### SRS-162: Reporting (SRS Object Type)
- Type: Section

##### SRS-163 (SRS Object Type)
The application shall allow users to print the displayed requirements table.
- Status: Released
- Type: Requirement
- Ver. Method: Test
- Satisfaction -> NEEDS-23
- Satisfaction -> NEEDS-29

##### SRS-164 (SRS Object Type)
The application shall allow users to create a PDF containing the displayed requirements table.
- Status: Released
- Type: Requirement
- Ver. Method: Test
- Satisfaction -> NEEDS-23
- Satisfaction -> NEEDS-29

### SRS-23: Usability requirements (SRS Object Type)
- Type: Section

### SRS-24: Performance requirements (SRS Object Type)
- Type: Section

#### SRS-174: Startup Time (SRS Object Type)
The application should display the opened document within 10s after it is started.
- Type: Requirement
- Satisfaction -> NEEDS-39

#### SRS-171: Edit Response Time (SRS Object Type)
The application should display updated values within 1s after user triggers the edit operation.
- Type: Requirement
- Satisfaction -> NEEDS-41

#### SRS-173: Smooth Scrolling (SRS Object Type)
While a user scrolls the requirements table, the application should not display scrolling jerks longer than 200ms.
- Type: Requirement
- Satisfaction -> NEEDS-44

#### SRS-170: Document Size (SRS Object Type)
The application shall allow users to open documents up to 10000 objects and 100 file attachments with total size up to 100MB.
- Type: Requirement
- Satisfaction -> NEEDS-44

### SRS-25: Logical database requirements (SRS Object Type)
- Type: Section

### SRS-26: Design constraints (SRS Object Type)
- Type: Section

### SRS-27: Standards compliance (SRS Object Type)
- Type: Section

#### SRS-204 (SRS Object Type)
The application shall comply with OWASP Application Security Verification Standard (ASVS) - Level 1, see document [DEMO-ASVS].
- Type: Requirement

### SRS-28: Software system attributes (SRS Object Type)
- Type: Section

#### SRS-212: Security (SRS Object Type)
- Type: Section

##### SRS-224: Secure Input (SRS Object Type)
- Type: Section

###### SRS-205 (SRS Object Type)
The application shall validate all inputs entered by users.
- Type: Requirement
- Satisfaction -> ASVS-232
- Satisfaction -> ASVS-233

###### SRS-206 (SRS Object Type)
The application shall sanitize all inputs entered by users in a rich text editor.
- Type: Requirement
- Satisfaction -> ASVS-236

###### SRS-199 (SRS Object Type)
The application shall sanitize all inputs imported by users.
- Type: Requirement
- Satisfaction -> NEEDS-42
- Satisfaction -> ASVS-236

###### SRS-207 (SRS Object Type)
The application shall prevent user to attach an executable file to project data.
- Type: Requirement
- Satisfaction -> ASVS-237

###### SRS-211 (SRS Object Type)
The application shall not display preview of insecure SVG image attachments.
- Type: Requirement
- Satisfaction -> ASVS-242

###### SRS-208 (SRS Object Type)
The application shall prevent user to attach a file larger than 10 MBs.
- Type: Requirement
- Satisfaction -> ASVS-237

###### SRS-209 (SRS Object Type)
The application shall not execute any code provided by users, which is not sanitized or running in a sandbox.
- Type: Requirement
- Satisfaction -> ASVS-239
- Satisfaction -> ASVS-240

###### SRS-218 (SRS Object Type)
The application shall be protected against JSON injection attacks, JSON eval attacks, and JavaScript expression evaluation.
- Type: Requirement
- Satisfaction -> ASVS-250
- Satisfaction -> ASVS-263

##### SRS-225: Secure Output (SRS Object Type)
- Type: Section

###### SRS-217 (SRS Object Type)
The application shall escape all HTML exports.
- Type: Requirement
- Satisfaction -> ASVS-245
- Satisfaction -> ASVS-246
- Satisfaction -> ASVS-247

##### SRS-226: Sensitive Data Handling (SRS Object Type)
- Type: Section

###### SRS-219 (SRS Object Type)
The application shall not store sensitive data in application logs.
- Type: Requirement
- Satisfaction -> ASVS-287
- Satisfaction -> ASVS-288

###### SRS-220 (SRS Object Type)
The application privacy policy shall clearly explain how personal and project data are processed.
- Type: Requirement
- Satisfaction -> ASVS-318
- Satisfaction -> ASVS-319

##### SRS-223: Secure Build (SRS Object Type)
- Type: Section

###### SRS-228 (SRS Object Type)
The application source and configuration files shall be managed under a version control system.
- Type: Requirement
- Satisfaction -> ASVS-407

###### SRS-222 (SRS Object Type)
The application shall be build in a secure image separated from the host environment.
- Type: Requirement
- Satisfaction -> ASVS-403
- Satisfaction -> ASVS-406

###### SRS-227 (SRS Object Type)
The application build shall be reproducible.
- Type: Requirement
- Satisfaction -> ASVS-406

###### SRS-229 (SRS Object Type)
The application 3rd party dependencies shall be updated before building binaries.
- Type: Requirement
- Satisfaction -> ASVS-409

###### SRS-230 (SRS Object Type)
Unused application features, configurations, and 3rd party dependencies shall be removed before building binaries.
- Type: Requirement
- Satisfaction -> ASVS-410

###### SRS-221 (SRS Object Type)
The application executable binaries shall be digitally signed.
- Type: Requirement
- Satisfaction -> ASVS-347

#### SRS-215: Portability (SRS Object Type)
- Type: Section

##### SRS-195 (SRS Object Type)
The application shall run on Windows, Linux or Mac operating systems.
- Status: Released
- Type: Requirement
- Ver. Method: Test
- Satisfaction -> NEEDS-51

# Specification: TESTS
- ReqIF.Description: ReqView Verification Tests

## TESTS-2: Test Cases (TESTS Object Type)
- Type: Section

### TESTS-3: File Operations (TESTS Object Type)
- Type: Section

#### TESTS-4: Open Local File (TESTS Object Type)
- Status: Passed
- Type: Section

##### TESTS-9: File Open Success (TESTS Object Type)
- Status: Passed
- Type: Section

###### TESTS-19 (TESTS Object Type)
Edit the first object by deleting its description.
- Precondition: Clean demo document is opened.
- Type: Requirement
- Verification -> SRS-56

###### TESTS-11 (TESTS Object Type)
Select File / Open (CTRL+O) from menu.
- Expected Result: Dialog "Save changes?" is shown.
- Type: Requirement

###### TESTS-20 (TESTS Object Type)
Choose "Do not save" in "Save changes?" dialog.
- Expected Result: System file selection Open dialog is shown.
- Type: Requirement

###### TESTS-12 (TESTS Object Type)
In the Open dialog choose a ReqView project file (*.reqw) and click Open button.
- Test Data: data/reqview_demo.reqw
- Expected Result: The project from the file is successfully opened.
  The current document is the last active document from the project.
- Type: Requirement

##### TESTS-10: File Open Failure (TESTS Object Type)
- Status: Passed
- Type: Section

###### TESTS-15 (TESTS Object Type)
Select File / Open (CTRL+O) from menu.
- Expected Result: Open dialog is shown.
- Type: Requirement

###### TESTS-16 (TESTS Object Type)
In the Open dialog choose a file which is not a valid ReqView project file and click Open button.
- Test Data: data/reqview_export.csv
- Expected Result: Error message "Error during opening file!" is displayed.
- Type: Requirement

#### TESTS-5: Save Local File (TESTS Object Type)
- Status: Draft
- Type: Requirement
- Verification -> SRS-59

### TESTS-6: Edit Requirements (TESTS Object Type)
- Type: Section

#### TESTS-21: Create Requirements (TESTS Object Type)
- Status: Draft
- Type: Requirement
- Verification -> SRS-53
- Verification -> SRS-106
- Verification -> SRS-107
- Verification -> SRS-114
- Verification -> SRS-115
- Verification -> SRS-116

#### TESTS-22: Restructure Requirement (TESTS Object Type)
- Status: Draft
- Type: Requirement
- Verification -> SRS-108
- Verification -> SRS-109
- Verification -> SRS-110
- Verification -> SRS-111
- Verification -> SRS-112

#### TESTS-29: Custom Attributes (TESTS Object Type)
- Status: Draft
- Type: Requirement
- Verification -> SRS-119
- Verification -> SRS-120
- Verification -> SRS-121
- Verification -> SRS-122
- Verification -> SRS-157
- Verification -> SRS-165
- Verification -> SRS-191
- Verification -> SRS-192
- Verification -> SRS-193

#### TESTS-30: Discussion (TESTS Object Type)
- Status: Draft
- Type: Requirement
- Verification -> SRS-90
- Verification -> SRS-96
- Verification -> SRS-97
- Verification -> SRS-98
- Verification -> SRS-132
- Verification -> SRS-133

# Specification: ARCH
- ReqIF.Description: ReqView Architecture

## ARCH-2: Architecture (ARCH Object Type)
- Type: Section

### ARCH-18: Application (ARCH Object Type)
- Type: Section

#### ARCH-8: Widgets (ARCH Object Type)
Widgets displayed in the UI triggering events based on an user input
- Type: Requirement
- Implementation -> SRS-80
- Implementation -> SRS-81
- Implementation -> SRS-83
- Implementation -> SRS-84
- Implementation -> SRS-85
- Implementation -> SRS-86
- Implementation -> SRS-87
- Implementation -> SRS-88
- Implementation -> SRS-89
- Implementation -> SRS-90
- Implementation -> SRS-92
- Implementation -> SRS-93
- Implementation -> SRS-94
- Implementation -> SRS-96
- Implementation -> SRS-97
- Implementation -> SRS-98
- Implementation -> SRS-99
- Implementation -> SRS-101
- Implementation -> SRS-102
- Implementation -> SRS-103
- Implementation -> SRS-114
- Implementation -> SRS-115
- Implementation -> SRS-116
- Implementation -> SRS-142
- Implementation -> SRS-147
- Implementation -> SRS-148
- Implementation -> SRS-149
- Implementation -> SRS-150
- Implementation -> SRS-152
- Implementation -> SRS-153
- Implementation -> SRS-165
- Implementation -> SRS-171
- Implementation -> SRS-173
- Implementation -> SRS-190
- Implementation -> SRS-199
- Usage -> ARCH-9

#### ARCH-9: Actions (ARCH Object Type)
UI actions called from UI widgets based on UI events
- Type: Requirement
- Implementation -> SRS-53
- Implementation -> SRS-54
- Implementation -> SRS-56
- Implementation -> SRS-59
- Implementation -> SRS-61
- Implementation -> SRS-63
- Implementation -> SRS-72
- Implementation -> SRS-73
- Implementation -> SRS-76
- Implementation -> SRS-77
- Implementation -> SRS-106
- Implementation -> SRS-108
- Implementation -> SRS-109
- Implementation -> SRS-110
- Implementation -> SRS-111
- Implementation -> SRS-112
- Implementation -> SRS-119
- Implementation -> SRS-122
- Implementation -> SRS-124
- Implementation -> SRS-127
- Implementation -> SRS-128
- Implementation -> SRS-129
- Implementation -> SRS-132
- Implementation -> SRS-135
- Implementation -> SRS-137
- Implementation -> SRS-138
- Implementation -> SRS-139
- Implementation -> SRS-140
- Implementation -> SRS-141
- Implementation -> SRS-156
- Implementation -> SRS-160
- Implementation -> SRS-161
- Implementation -> SRS-163
- Implementation -> SRS-164
- Implementation -> SRS-192
- Usage -> ARCH-10
- Usage -> ARCH-12
- Usage -> ARCH-13
- Usage -> ARCH-14
- Usage -> ARCH-16

#### ARCH-10: Dialogs (ARCH Object Type)
UI dialogs opened from UI actions
- Type: Requirement
- Implementation -> SRS-199

#### ARCH-11: Commands (ARCH Object Type)
Commands called from the CLI
- Type: Requirement
- Usage -> ARCH-12
- Usage -> ARCH-14

#### ARCH-14: Export (ARCH Object Type)
Exporters of project data to supported external file formats
- Type: Requirement
- Implementation -> SRS-76
- Implementation -> SRS-77
- Usage -> ARCH-17

#### ARCH-13: Import (ARCH Object Type)
Importers of project data from supported external file formats
- Type: Requirement
- Implementation -> SRS-72
- Implementation -> SRS-73
- Implementation -> SRS-199
- Usage -> ARCH-17

#### ARCH-16: File (ARCH Object Type)
ReqView Project File / Folder readers and writers
- Type: Requirement
- Implementation -> SRS-56
- Implementation -> SRS-59
- Implementation -> SRS-62
- Implementation -> SRS-199

#### ARCH-17: Tools (ARCH Object Type)
Various tools for data conversion and formatting
- Type: Requirement

#### ARCH-12: Models (ARCH Object Type)
Data models storing project data and user preferences
- Type: Requirement
- Implementation -> SRS-106
- Implementation -> SRS-107
- Implementation -> SRS-108
- Implementation -> SRS-109
- Implementation -> SRS-110
- Implementation -> SRS-111
- Implementation -> SRS-112
- Implementation -> SRS-114
- Implementation -> SRS-115
- Implementation -> SRS-119
- Implementation -> SRS-120
- Implementation -> SRS-121
- Implementation -> SRS-122
- Implementation -> SRS-124
- Implementation -> SRS-126
- Implementation -> SRS-127
- Implementation -> SRS-128
- Implementation -> SRS-129
- Implementation -> SRS-132
- Implementation -> SRS-133
- Implementation -> SRS-135
- Implementation -> SRS-137
- Implementation -> SRS-138
- Implementation -> SRS-139
- Implementation -> SRS-140
- Implementation -> SRS-141
- Implementation -> SRS-144
- Implementation -> SRS-156
- Implementation -> SRS-157
- Implementation -> SRS-159
- Implementation -> SRS-161
- Implementation -> SRS-165
- Implementation -> SRS-170
- Implementation -> SRS-171
- Implementation -> SRS-173
- Implementation -> SRS-191
- Implementation -> SRS-192
- Implementation -> SRS-193
- Usage -> ARCH-15

#### ARCH-15: Persistency (ARCH Object Type)
Application persistency readers and writers
- Type: Requirement
- Implementation -> SRS-144
- Implementation -> SRS-160
- Implementation -> SRS-170
